-- SCCS id:	@(#)h245_globals.asn	7.1.2.1	10/25/99	

-- ------------------------------------------------------------- --
--               Copyright (c) 1996-1998 Lucent Technologies
--                       All Rights Reserved
-- 
--                       THIS IS UNPUBLISHED
--                       PROPRIETARY SOURCE
--                   CODE OF Lucent Technologies
-- 
--           The copyright notice above does not evidence any
--          actual or intended publication of such source code
-- 
--	CVS Information:
--<COMMENT  "$Revision: 1.4 $  $Date: 1999/03/15 21:05:33 $">--
--
--  Filename       :   h225_globals.asn
--  Description    :   This file contains the OSS
--                      ASN.1 compiler directives.
--  Caveats        :   ASN.1 compiler version: 5.0.3
--
--  Revision History
--  Date			Revision description
--  06/11/1998	File Created
--	11/09/1998	Updated to use OSS ASN.1 Tools version 5.0.3.
-- 
-- ------------------------------------------------------------- --

--<OSS.OBJECTID LONG>--
--<OSS. NOPOINTER>--
--<OSS.
--  UNBOUNDED SEQUENCE OF, SET OF, OBJECT IDENTIFIER>--

--<ASN1.Version 1997 MULTIMEDIA-SYSTEM-CONTROL>--

-- ------------------------------------------------------------- --
-- OctetString						::= OCTET STRING
-- ------------------------------------------------------------- --

--<OSS.TYPENAME
--		MULTIMEDIA-SYSTEM-CONTROL.OctetString
--		"EmOctetString">--

-- ------------------------------------------------------------- --
-- ObjectIdentifier				::= OBJECT IDENTIFIER
-- ------------------------------------------------------------- --

--<OSS.TYPENAME
--		MULTIMEDIA-SYSTEM-CONTROL.ObjectIdentifier
--		"EmObjectIdentifier">--

-- ------------------------------------------------------------- --
-- SeqOfDataApplicationCapability	::= SEQUENCE OF DataApplicationCapability
-- ------------------------------------------------------------- --

--<ASN1.PDU
--		MULTIMEDIA-SYSTEM-CONTROL.SeqOfDataApplicationCapability>--
--<OSS.TYPENAME
--		MULTIMEDIA-SYSTEM-CONTROL.SeqOfDataApplicationCapability
--		"EmSeqOfDataApplicationCapability">--

-- ------------------------------------------------------------- --
-- SeqOfNonStandardParameter		::= SEQUENCE OF NonStandardParameter
-- ------------------------------------------------------------- --

--<OSS.TYPENAME
--		MULTIMEDIA-SYSTEM-CONTROL.SeqOfNonStandardParameter
--		"EmSeqOfNonStandardParameter">--

-- ------------------------------------------------------------- --
-- SeqOfTerminalInformation		::= SEQUENCE OF TerminalInformation
-- ------------------------------------------------------------- --

--<ASN1.PDU
--		MULTIMEDIA-SYSTEM-CONTROL.SeqOfTerminalInformation>--
--<OSS.TYPENAME
--		MULTIMEDIA-SYSTEM-CONTROL.SeqOfTerminalInformation
--		"EmSeqOfTerminalInformation">--

-- ------------------------------------------------------------- --
-- SeqOf256RTPPayloadType			::= SEQUENCE SIZE(1..256) OF RTPPayloadType
-- ------------------------------------------------------------- --

--<ASN1.PDU
--		MULTIMEDIA-SYSTEM-CONTROL.SeqOf256RTPPayloadType>--
--<OSS.TYPENAME
--		MULTIMEDIA-SYSTEM-CONTROL.SeqOf256RTPPayloadType
--		"EmSeqOf256RTPPayloadType">--

-- ------------------------------------------------------------- --
-- SeqOf256QOSCapability			::= SEQUENCE SIZE(1..256) OF QOSCapability
-- ------------------------------------------------------------- --

--<ASN1.PDU
--		MULTIMEDIA-SYSTEM-CONTROL.SeqOf256QOSCapability>--
--<OSS.TYPENAME
--		MULTIMEDIA-SYSTEM-CONTROL.SeqOf256QOSCapability
--		"EmSeqOf256QOSCapability">--

-- ------------------------------------------------------------- --
-- SeqOf16NonStandardParameter		::= SEQUENCE SIZE(1..16) OF NonStandardParameter
-- ------------------------------------------------------------- --

--<ASN1.PDU
--		MULTIMEDIA-SYSTEM-CONTROL.SeqOf16NonStandardParameter>--
--<OSS.TYPENAME
--		MULTIMEDIA-SYSTEM-CONTROL.SeqOf16NonStandardParameter
--		"EmSeqOf16NonStandardParameter">--

-- ------------------------------------------------------------- --
-- SeqOf256EscrowData				::= SEQUENCE SIZE(1..256) OF EscrowData
-- ------------------------------------------------------------- --

--<ASN1.PDU
--		MULTIMEDIA-SYSTEM-CONTROL.SeqOf256EscrowData>--
--<OSS.TYPENAME
--		MULTIMEDIA-SYSTEM-CONTROL.SeqOf256EscrowData
--		"EmSeqOf256EscrowData">--

-- ------------------------------------------------------------- --
-- SeqOf256MultiplexElement		::= SEQUENCE SIZE (1..256) OF MultiplexElement
-- ------------------------------------------------------------- --

--<ASN1.Remove
--		MULTIMEDIA-SYSTEM-CONTROL.SeqOf256MultiplexElement>--

-- ------------------------------------------------------------- --
-- SeqOf2to255MultiplexElement		::= SEQUENCE SIZE (2..255) OF MultiplexElement
-- ------------------------------------------------------------- --

--<ASN1.Remove
--		MULTIMEDIA-SYSTEM-CONTROL.SeqOf2to255MultiplexElement>--

-- ------------------------------------------------------------- --
-- SeqOf256ModeDescription ::= SEQUENCE SIZE (1..256) OF ModeDescription
-- ------------------------------------------------------------- --

--<ASN1.PDU
--		MULTIMEDIA-SYSTEM-CONTROL.SeqOf256ModeDescription>--
--<OSS.TYPENAME
--		MULTIMEDIA-SYSTEM-CONTROL.SeqOf256ModeDescription
--		"EmSeqOf256ModeDescription">--

-- ------------------------------------------------------------- --
-- SeqOf16Criteria	::= SEQUENCE SIZE (1..16) OF Criteria
-- ------------------------------------------------------------- --

--<ASN1.PDU
--		MULTIMEDIA-SYSTEM-CONTROL.SeqOf16Criteria>--
--<OSS.TYPENAME
--		MULTIMEDIA-SYSTEM-CONTROL.SeqOf16Criteria
--		"EmSeqOf16Criteria">--

-- ------------------------------------------------------------- --
-- SeqOfMediaDistributionCapability ::= SEQUENCE OF MediaDistributionCapability
-- ------------------------------------------------------------- --

--<ASN1.PDU
--		MULTIMEDIA-SYSTEM-CONTROL.SeqOfMediaDistributionCapability>--
--<OSS.TYPENAME
--		MULTIMEDIA-SYSTEM-CONTROL.SeqOfMediaDistributionCapability
--		"EmSeqOfMediaDistributionCapability">--

-- ------------------------------------------------------------- --
-- SeqOf256CapabilityTableEntryNumber ::= SEQUENCE SIZE (1..256) OF CapabilityTableEntryNumber
-- ------------------------------------------------------------- --

--<ASN1.PDU
--		MULTIMEDIA-SYSTEM-CONTROL.SeqOf256CapabilityTableEntryNumber>--
--<OSS.TYPENAME
--		MULTIMEDIA-SYSTEM-CONTROL.SeqOf256CapabilityTableEntryNumber
--		"EmSeqOf256CapabilityTableEntryNumber">--

-- ------------------------------------------------------------- --
-- SeqOf256RedundancyEncodingCapability ::= SEQUENCE SIZE(1..256) OF RedundancyEncodingCapability
-- ------------------------------------------------------------- --

--<ASN1.PDU
--		MULTIMEDIA-SYSTEM-CONTROL.SeqOf256RedundancyEncodingCapability>--
--<OSS.TYPENAME
--		MULTIMEDIA-SYSTEM-CONTROL.SeqOf256RedundancyEncodingCapability
--		"EmSeqOf256RedundancyEncodingCapability">--

-- ------------------------------------------------------------- --
-- SeqOf256MediaChannelCapability ::= SEQUENCE SIZE(1..256) OF MediaChannelCapability
-- ------------------------------------------------------------- --

--<ASN1.PDU
--		MULTIMEDIA-SYSTEM-CONTROL.SeqOf256MediaChannelCapability>--
--<OSS.TYPENAME
--		MULTIMEDIA-SYSTEM-CONTROL.SeqOf256MediaChannelCapability
--		"EmSeqOf256MediaChannelCapability">--

-- ------------------------------------------------------------- --
-- SeqOf256RTPH263VideoRedundancyFrameMapping ::= SEQUENCE SIZE(1..256) OF RTPH263VideoRedundancyFrameMapping
-- ------------------------------------------------------------- --

--<ASN1.PDU
--		MULTIMEDIA-SYSTEM-CONTROL.SeqOf256RTPH263VideoRedundancyFrameMapping>--
--<OSS.TYPENAME
--		MULTIMEDIA-SYSTEM-CONTROL.SeqOf256RTPH263VideoRedundancyFrameMapping
--		"EmSeqOf256RTPH263VideoRedundancyFrameMapping">--

-- ------------------------------------------------------------- --
-- SeqOf256MediaEncryptionAlgorithm ::= SEQUENCE SIZE(1..256) OF MediaEncryptionAlgorithm
-- ------------------------------------------------------------- --

--<ASN1.PDU
--		MULTIMEDIA-SYSTEM-CONTROL.SeqOf256MediaEncryptionAlgorithm>--
--<OSS.TYPENAME
--		MULTIMEDIA-SYSTEM-CONTROL.SeqOf256MediaEncryptionAlgorithm
--		"EmSeqOf256MediaEncryptionAlgorithm">--

-- ------------------------------------------------------------- --
-- SetOfVCCapability 			 ::= SET OF VCCapability
-- ------------------------------------------------------------- --

--<ASN1.Remove
--		MULTIMEDIA-SYSTEM-CONTROL.SetOfVCCapability>--

-- ------------------------------------------------------------- --
-- SetOf256CapabilityTableEntry ::= SET SIZE (1..256) OF CapabilityTableEntry
-- ------------------------------------------------------------- --

--<ASN1.PDU
--		MULTIMEDIA-SYSTEM-CONTROL.SetOf256CapabilityTableEntry>--
--<OSS.TYPENAME
--		MULTIMEDIA-SYSTEM-CONTROL.SetOf256CapabilityTableEntry
--		"EmSetOf256CapabilityTableEntry">--

-- ------------------------------------------------------------- --
-- SetOf256CapabilityDescriptor ::= SET SIZE (1..256) OF CapabilityDescriptor
-- ------------------------------------------------------------- --

--<ASN1.PDU
--		MULTIMEDIA-SYSTEM-CONTROL.SetOf256CapabilityDescriptor>--
--<OSS.TYPENAME
--		MULTIMEDIA-SYSTEM-CONTROL.SetOf256CapabilityDescriptor
--		"EmSetOf256CapabilityDescriptor">--

-- ------------------------------------------------------------- --
-- SetOf14INTEGER14 			 ::= SET SIZE (1..14) OF INTEGER(1..14)
-- ------------------------------------------------------------- --

--<ASN1.PDU
--		MULTIMEDIA-SYSTEM-CONTROL.SetOf14INTEGER14>--
--<OSS.TYPENAME
--		MULTIMEDIA-SYSTEM-CONTROL.SetOf14INTEGER14
--		"EmSetOf14INTEGER14">--

-- ------------------------------------------------------------- --
-- SetOf16CustomPictureFormat	 ::= SET SIZE (1..16) OF CustomPictureFormat
-- ------------------------------------------------------------- --

--<ASN1.PDU
--		MULTIMEDIA-SYSTEM-CONTROL.SetOf16CustomPictureFormat>--
--<OSS.TYPENAME
--		MULTIMEDIA-SYSTEM-CONTROL.SetOf16CustomPictureFormat
--		"EmSetOf16CustomPictureFormat">--

-- ------------------------------------------------------------- --
-- SetOf16H263VideoModeCombos	 ::= SET SIZE (1..16) OF H263VideoModeCombos
-- ------------------------------------------------------------- --

--<ASN1.PDU
--		MULTIMEDIA-SYSTEM-CONTROL.SetOf16H263VideoModeCombos>--
--<OSS.TYPENAME
--		MULTIMEDIA-SYSTEM-CONTROL.SetOf16H263VideoModeCombos
--		"EmSetOf16H263VideoModeCombos">--

-- ------------------------------------------------------------- --
-- SetOf16H263ModeComboFlags	 ::= SET SIZE (1..16) OF H263ModeComboFlags
-- ------------------------------------------------------------- --

--<ASN1.PDU
--		MULTIMEDIA-SYSTEM-CONTROL.SetOf16H263ModeComboFlags>--
--<OSS.TYPENAME
--		MULTIMEDIA-SYSTEM-CONTROL.SetOf16H263ModeComboFlags
--		"EmSetOf16H263ModeComboFlags">--

-- ------------------------------------------------------------- --
-- SetOf14EnhancementOptions 	 ::= SET SIZE(1..14) OF EnhancementOptions
-- ------------------------------------------------------------- --

--<ASN1.PDU
--		MULTIMEDIA-SYSTEM-CONTROL.SetOf14EnhancementOptions>--
--<OSS.TYPENAME
--		MULTIMEDIA-SYSTEM-CONTROL.SetOf14EnhancementOptions
--		"EmSetOf14EnhancementOptions">--

-- ------------------------------------------------------------- --
-- SetOf256ModeElement 		 ::= SET SIZE (1..256) OF ModeElement
-- ------------------------------------------------------------- --

--<ASN1.PDU
--		MULTIMEDIA-SYSTEM-CONTROL.SetOf256ModeElement>--
--<OSS.TYPENAME
--		MULTIMEDIA-SYSTEM-CONTROL.SetOf256ModeElement
--		"EmSetOf256ModeElement">--

-- ------------------------------------------------------------- --
-- SetOf256TerminalLabel 		 ::= SET SIZE (1..256) OF TerminalLabel
-- ------------------------------------------------------------- --

--<ASN1.PDU
--		MULTIMEDIA-SYSTEM-CONTROL.SetOf256TerminalLabel>--
--<OSS.TYPENAME
--		MULTIMEDIA-SYSTEM-CONTROL.SetOf256TerminalLabel
--		"EmSetOf256TerminalLabel">--

-- ------------------------------------------------------------- --
-- SetOf14BEnhancementParameters ::= SET SIZE(1..14) OF BEnhancementParameters
-- ------------------------------------------------------------- --

--<ASN1.PDU
--		MULTIMEDIA-SYSTEM-CONTROL.SetOf14BEnhancementParameters>--
--<OSS.TYPENAME
--		MULTIMEDIA-SYSTEM-CONTROL.SetOf14BEnhancementParameters
--		"EmSetOf14BEnhancementParameters">--

-- ------------------------------------------------------------- --
-- SetOf15MultiplexEntryDescriptor ::= SET SIZE (1..15) OF MultiplexEntryDescriptor
-- ------------------------------------------------------------- --

--<ASN1.Remove
--		MULTIMEDIA-SYSTEM-CONTROL.SetOf15MultiplexEntryDescriptor>--

-- ------------------------------------------------------------- --
-- SetOf256AlternativeCapabilitySet ::= SET SIZE (1..256) OF AlternativeCapabilitySet
-- ------------------------------------------------------------- --

--<ASN1.PDU
--		MULTIMEDIA-SYSTEM-CONTROL.SetOf256AlternativeCapabilitySet>--
--<OSS.TYPENAME
--		MULTIMEDIA-SYSTEM-CONTROL.SetOf256AlternativeCapabilitySet
--		"EmSetOf256AlternativeCapabilitySet">--

-- ------------------------------------------------------------- --
-- SetOf16CustomPictureClockFrequency ::= SET SIZE (1..16) OF CustomPictureClockFrequency
-- ------------------------------------------------------------- --

--<ASN1.PDU
--		MULTIMEDIA-SYSTEM-CONTROL.SetOf16CustomPictureClockFrequency>--
--<OSS.TYPENAME
--		MULTIMEDIA-SYSTEM-CONTROL.SetOf16CustomPictureClockFrequency
--		"EmSetOf16CustomPictureClockFrequency">--

-- ------------------------------------------------------------- --
-- SetOf15MultiplexTableEntryNumber ::= SET SIZE (1..15) OF MultiplexTableEntryNumber
-- ------------------------------------------------------------- --

--<ASN1.Remove
--		MULTIMEDIA-SYSTEM-CONTROL.SetOf15MultiplexTableEntryNumber>--

-- ------------------------------------------------------------- --
-- SetOf15MultiplexEntryRejectionDescriptions ::= SET SIZE (1..15) OF MultiplexEntryRejectionDescriptions
-- ------------------------------------------------------------- --

--<ASN1.Remove
--		MULTIMEDIA-SYSTEM-CONTROL.SetOf15MultiplexEntryRejectionDescriptions>--

-- ------------------------------------------------------------- --
-- SetOf15RequestMultiplexEntryRejectionDescriptions ::= SET SIZE (1..15) OF RequestMultiplexEntryRejectionDescriptions
-- ------------------------------------------------------------- --

--<ASN1.Remove
--		MULTIMEDIA-SYSTEM-CONTROL.SetOf15RequestMultiplexEntryRejectionDescriptions>--

-- ------------------------------------------------------------- --
-- SetOf256CommunicationModeTableEntry ::= SET SIZE(1..256) OF CommunicationModeTableEntry
-- ------------------------------------------------------------- --

--<ASN1.PDU
--		MULTIMEDIA-SYSTEM-CONTROL.SetOf256CommunicationModeTableEntry>--
--<OSS.TYPENAME
--		MULTIMEDIA-SYSTEM-CONTROL.SetOf256CommunicationModeTableEntry
--		"EmSetOf256CommunicationModeTableEntry">--

-- ------------------------------------------------------------- --
-- SetOf64kCapabilityTableEntryNumber ::= SET SIZE (1..65535) OF CapabilityTableEntryNumber
-- ------------------------------------------------------------- --

--<ASN1.PDU
--		MULTIMEDIA-SYSTEM-CONTROL.SetOf64kCapabilityTableEntryNumber>--
--<OSS.TYPENAME
--		MULTIMEDIA-SYSTEM-CONTROL.SetOf64kCapabilityTableEntryNumber
--		"EmSetOf64kCapabilityTableEntryNumber">--

-- ------------------------------------------------------------- --
-- SetOf256CapabilityDescriptorNumber ::= SET SIZE (1..256) OF CapabilityDescriptorNumber
-- ------------------------------------------------------------- --

--<ASN1.PDU
--		MULTIMEDIA-SYSTEM-CONTROL.SetOf256CapabilityDescriptorNumber>--
--<OSS.TYPENAME
--		MULTIMEDIA-SYSTEM-CONTROL.SetOf256CapabilityDescriptorNumber
--		"EmSetOf256CapabilityDescriptorNumber">-- 

-- ==============================================================
-- Top level Messages
-- ==============================================================

-- -------------------------------------------------------------- --
--
-- MultimediaSystemControlMessage	::= CHOICE
-- {
-- 	    request	    RequestMessage,
-- 	    response	ResponseMessage,
-- 	    command	    CommandMessage,
-- 	    indication	IndicationMessage,
-- 	    ...
-- }
--
-- -------------------------------------------------------------- --

--<ASN1.PDU
--		MULTIMEDIA-SYSTEM-CONTROL.MultimediaSystemControlMessage>--
--<OSS.TYPENAME
--		MULTIMEDIA-SYSTEM-CONTROL.MultimediaSystemControlMessage
--		"EmMSCM">--
--<OSS.FIELDNAME
--		MULTIMEDIA-SYSTEM-CONTROL.MultimediaSystemControlMessage.request
--		"request">--
--<OSS.DefineName
--		MULTIMEDIA-SYSTEM-CONTROL.MultimediaSystemControlMessage.request
--		"EM_request">--
--<OSS.FIELDNAME
--		MULTIMEDIA-SYSTEM-CONTROL.MultimediaSystemControlMessage.response
--		"response">--
--<OSS.DefineName
--		MULTIMEDIA-SYSTEM-CONTROL.MultimediaSystemControlMessage.response
--		"response">--
--<OSS.DefineName
--		MULTIMEDIA-SYSTEM-CONTROL.MultimediaSystemControlMessage.response
--		"EM_response">--
--<OSS.FIELDNAME
--		MULTIMEDIA-SYSTEM-CONTROL.MultimediaSystemControlMessage.command
--		"command">--
--<OSS.DefineName
--		MULTIMEDIA-SYSTEM-CONTROL.MultimediaSystemControlMessage.command
--		"EM_command">--
--<OSS.FIELDNAME
--		MULTIMEDIA-SYSTEM-CONTROL.MultimediaSystemControlMessage.indication
--		"indication">--
--<OSS.DefineName
--		MULTIMEDIA-SYSTEM-CONTROL.MultimediaSystemControlMessage.indication
--		"EM_indication">--

-- -------------------------------------------------------------- --
--
-- RequestMessage  ::= CHOICE
-- {
--     nonStandard                 NonStandardMessage,
--     masterSlaveDetermination    MasterSlaveDetermination,
--     terminalCapabilitySet       TerminalCapabilitySet,
--     openLogicalChannel          OpenLogicalChannel,
--     closeLogicalChannel         CloseLogicalChannel,
--     requestChannelClose         RequestChannelClose,
--     multiplexEntrySend          MultiplexEntrySend,
--     requestMultiplexEntry       RequestMultiplexEntry,
--     requestMode                 RequestMode,
--     roundTripDelayRequest       RoundTripDelayRequest,
--     maintenanceLoopRequest      MaintenanceLoopRequest,
--     ...,
--     communicationModeRequest    CommunicationModeRequest,
--     conferenceRequest           ConferenceRequest,
-- }
--
-- -------------------------------------------------------------- --

--<ASN1.PDU
--		MULTIMEDIA-SYSTEM-CONTROL.RequestMessage>--
--<OSS.TYPENAME
--		MULTIMEDIA-SYSTEM-CONTROL.RequestMessage
--		"EmRequestMessage">--
--<OSS.FIELDNAME
--		MULTIMEDIA-SYSTEM-CONTROL.RequestMessage.nonStandard
--		"nonStandard">--
--<OSS.DefineName
--		MULTIMEDIA-SYSTEM-CONTROL.RequestMessage.nonStandard
--		"EM_RequestMessage_nonStandard">--
--<OSS.FIELDNAME
--		MULTIMEDIA-SYSTEM-CONTROL.RequestMessage.masterSlaveDetermination
--		"masterSlaveDetermination">--
--<OSS.DefineName
--		MULTIMEDIA-SYSTEM-CONTROL.RequestMessage.masterSlaveDetermination
--		"EM_masterSlaveDetermination">--
--<OSS.FIELDNAME
--		MULTIMEDIA-SYSTEM-CONTROL.RequestMessage.terminalCapabilitySet
--		"terminalCapabilitySet">--
--<OSS.DefineName
--		MULTIMEDIA-SYSTEM-CONTROL.RequestMessage.terminalCapabilitySet
--		"EM_terminalCapabilitySet">--
--<OSS.FIELDNAME
--		MULTIMEDIA-SYSTEM-CONTROL.RequestMessage.openLogicalChannel
--		"openLogicalChannel">--
--<OSS.DefineName
--		MULTIMEDIA-SYSTEM-CONTROL.RequestMessage.openLogicalChannel
--		"EM_openLogicalChannel">--
--<OSS.FIELDNAME
--		MULTIMEDIA-SYSTEM-CONTROL.RequestMessage.closeLogicalChannel
--		"closeLogicalChannel">--
--<OSS.DefineName
--		MULTIMEDIA-SYSTEM-CONTROL.RequestMessage.closeLogicalChannel
--		"EM_closeLogicalChannel">--
--<OSS.FIELDNAME
--		MULTIMEDIA-SYSTEM-CONTROL.RequestMessage.requestChannelClose
--		"requestChannelClose">--
--<OSS.DefineName
--		MULTIMEDIA-SYSTEM-CONTROL.RequestMessage.requestChannelClose
--		"EM_requestChannelClose">--

--<ASN1.Remove
--		MULTIMEDIA-SYSTEM-CONTROL.RequestMessage.multiplexEntrySend>--

--<ASN1.Remove
--		MULTIMEDIA-SYSTEM-CONTROL.RequestMessage.requestMultiplexEntry>--

--<OSS.FIELDNAME
--		MULTIMEDIA-SYSTEM-CONTROL.RequestMessage.requestMode
--		"requestMode">--
--<OSS.DefineName
--		MULTIMEDIA-SYSTEM-CONTROL.RequestMessage.requestMode
--		"EM_requestMode">--
--<OSS.FIELDNAME
--		MULTIMEDIA-SYSTEM-CONTROL.RequestMessage.roundTripDelayRequest
--		"roundTripDelayRequest">--
--<OSS.DefineName
--		MULTIMEDIA-SYSTEM-CONTROL.RequestMessage.roundTripDelayRequest
--		"EM_roundTripDelayRequest">--
--<OSS.FIELDNAME
--		MULTIMEDIA-SYSTEM-CONTROL.RequestMessage.maintenanceLoopRequest
--		"maintenanceLoopRequest">--
--<OSS.DefineName
--		MULTIMEDIA-SYSTEM-CONTROL.RequestMessage.maintenanceLoopRequest
--		"EM_maintenanceLoopRequest">--
--<OSS.FIELDNAME
--		MULTIMEDIA-SYSTEM-CONTROL.RequestMessage.communicationModeRequest
--		"communicationModeRequest">--
--<OSS.DefineName
--		MULTIMEDIA-SYSTEM-CONTROL.RequestMessage.communicationModeRequest
--		"EM_communicationModeRequest">--
--<OSS.FIELDNAME
--		MULTIMEDIA-SYSTEM-CONTROL.RequestMessage.conferenceRequest
--		"conferenceRequest">--
--<OSS.DefineName
--		MULTIMEDIA-SYSTEM-CONTROL.RequestMessage.conferenceRequest
--		"EM_conferenceRequest">--

-- -------------------------------------------------------------- --
--
-- ResponseMessage ::= CHOICE
-- {
--     nonStandard NonStandardMessage,
--     masterSlaveDeterminationAck     MasterSlaveDeterminationAck,
--     masterSlaveDeterminationReject  MasterSlaveDeterminationReject,
--     terminalCapabilitySetAck        TerminalCapabilitySetAck,
--     terminalCapabilitySetReject     TerminalCapabilitySetReject,
--     openLogicalChannelAck           OpenLogicalChannelAck,
--     openLogicalChannelReject        OpenLogicalChannelReject,
--     closeLogicalChannelAck          CloseLogicalChannelAck,
--     requestChannelCloseAck          RequestChannelCloseAck,
--     requestChannelCloseReject       RequestChannelCloseReject,
--     multiplexEntrySendAck           MultiplexEntrySendAck,
--     multiplexEntrySendReject        MultiplexEntrySendReject,
--     requestMultiplexEntryAck        RequestMultiplexEntryAck,
--     requestMultiplexEntryReject     RequestMultiplexEntryReject,
--     requestModeAck                  RequestModeAck,
--     requestModeReject               RequestModeReject,
--     roundTripDelayResponse          RoundTripDelayResponse,
--     maintenanceLoopAck              MaintenanceLoopAck,
--     maintenanceLoopReject           MaintenanceLoopReject,
--     ...,
--     communicationModeResponse       CommunicationModeResponse,
--     conferenceResponse              ConferenceResponse
-- }
--
-- -------------------------------------------------------------- --

--<ASN1.PDU
--		MULTIMEDIA-SYSTEM-CONTROL.ResponseMessage>--
--<OSS.TYPENAME
--		MULTIMEDIA-SYSTEM-CONTROL.ResponseMessage
--		"EmResponseMessage">--
--<OSS.FIELDNAME
--		MULTIMEDIA-SYSTEM-CONTROL.ResponseMessage.nonStandard
--		"nonStandard">--
--<OSS.DefineName
--		MULTIMEDIA-SYSTEM-CONTROL.ResponseMessage.nonStandard
--		"EM_ResponseMessage_nonStandard">--
--<OSS.FIELDNAME
--		MULTIMEDIA-SYSTEM-CONTROL.ResponseMessage.masterSlaveDeterminationAck
--		"masterSlaveDeterminationAck">--
--<OSS.DefineName
--		MULTIMEDIA-SYSTEM-CONTROL.ResponseMessage.masterSlaveDeterminationAck
--		"EM_masterSlaveDeterminationAck">--
--<OSS.FIELDNAME
--		MULTIMEDIA-SYSTEM-CONTROL.ResponseMessage.masterSlaveDeterminationReject
--		"masterSlaveDeterminationReject">--
--<OSS.DefineName
--		MULTIMEDIA-SYSTEM-CONTROL.ResponseMessage.masterSlaveDeterminationReject
--		"EM_masterSlaveDeterminationReject">--
--<OSS.FIELDNAME
--		MULTIMEDIA-SYSTEM-CONTROL.ResponseMessage.terminalCapabilitySetAck
--		"terminalCapabilitySetAck">--
--<OSS.DefineName
--		MULTIMEDIA-SYSTEM-CONTROL.ResponseMessage.terminalCapabilitySetAck
--		"EM_terminalCapabilitySetAck">--
--<OSS.FIELDNAME
--		MULTIMEDIA-SYSTEM-CONTROL.ResponseMessage.terminalCapabilitySetReject
--		"terminalCapabilitySetReject">--
--<OSS.DefineName
--		MULTIMEDIA-SYSTEM-CONTROL.ResponseMessage.terminalCapabilitySetReject
--		"EM_terminalCapabilitySetReject">--
--<OSS.FIELDNAME
--		MULTIMEDIA-SYSTEM-CONTROL.ResponseMessage.openLogicalChannelAck
--		"openLogicalChannelAck">--
--<OSS.DefineName
--		MULTIMEDIA-SYSTEM-CONTROL.ResponseMessage.openLogicalChannelAck
--		"EM_openLogicalChannelAck">--
--<OSS.FIELDNAME
--		MULTIMEDIA-SYSTEM-CONTROL.ResponseMessage.openLogicalChannelReject
--		"openLogicalChannelReject">--
--<OSS.DefineName
--		MULTIMEDIA-SYSTEM-CONTROL.ResponseMessage.openLogicalChannelReject
--		"EM_openLogicalChannelReject">--
--<OSS.FIELDNAME
--		MULTIMEDIA-SYSTEM-CONTROL.ResponseMessage.closeLogicalChannelAck
--		"closeLogicalChannelAck">--
--<OSS.DefineName
--		MULTIMEDIA-SYSTEM-CONTROL.ResponseMessage.closeLogicalChannelAck
--		"EM_closeLogicalChannelAck">--
--<OSS.FIELDNAME
--		MULTIMEDIA-SYSTEM-CONTROL.ResponseMessage.requestChannelCloseAck
--		"requestChannelCloseAck">--
--<OSS.DefineName
--		MULTIMEDIA-SYSTEM-CONTROL.ResponseMessage.requestChannelCloseAck
--		"EM_requestChannelCloseAck">--
--<OSS.FIELDNAME
--		MULTIMEDIA-SYSTEM-CONTROL.ResponseMessage.requestChannelCloseReject
--		"requestChannelCloseReject">--
--<OSS.DefineName
--		MULTIMEDIA-SYSTEM-CONTROL.ResponseMessage.requestChannelCloseReject
--		"EM_requestChannelCloseReject">--

--<ASN1.Remove
--		MULTIMEDIA-SYSTEM-CONTROL.ResponseMessage.multiplexEntrySendAck>--

--<ASN1.Remove
--		MULTIMEDIA-SYSTEM-CONTROL.ResponseMessage.multiplexEntrySendReject>--

--<ASN1.Remove
--		MULTIMEDIA-SYSTEM-CONTROL.ResponseMessage.requestMultiplexEntryAck>--

--<ASN1.Remove
--		MULTIMEDIA-SYSTEM-CONTROL.ResponseMessage.requestMultiplexEntryReject>--

--<OSS.FIELDNAME
--		MULTIMEDIA-SYSTEM-CONTROL.ResponseMessage.requestModeAck
--		"requestModeAck">--
--<OSS.DefineName
--		MULTIMEDIA-SYSTEM-CONTROL.ResponseMessage.requestModeAck
--		"EM_requestModeAck">--
--<OSS.FIELDNAME
--		MULTIMEDIA-SYSTEM-CONTROL.ResponseMessage.requestModeReject
--		"requestModeReject">--
--<OSS.DefineName
--		MULTIMEDIA-SYSTEM-CONTROL.ResponseMessage.requestModeReject
--		"EM_requestModeReject">--
--<OSS.FIELDNAME
--		MULTIMEDIA-SYSTEM-CONTROL.ResponseMessage.roundTripDelayResponse
--		"roundTripDelayResponse">--
--<OSS.DefineName
--		MULTIMEDIA-SYSTEM-CONTROL.ResponseMessage.roundTripDelayResponse
--		"EM_roundTripDelayResponse">--
--<OSS.FIELDNAME
--		MULTIMEDIA-SYSTEM-CONTROL.ResponseMessage.maintenanceLoopAck
--		"maintenanceLoopAck">--
--<OSS.DefineName
--		MULTIMEDIA-SYSTEM-CONTROL.ResponseMessage.maintenanceLoopAck
--		"EM_maintenanceLoopAck">--
--<OSS.FIELDNAME
--		MULTIMEDIA-SYSTEM-CONTROL.ResponseMessage.maintenanceLoopReject
--		"maintenanceLoopReject">--
--<OSS.DefineName
--		MULTIMEDIA-SYSTEM-CONTROL.ResponseMessage.maintenanceLoopReject
--		"EM_maintenanceLoopReject">--
--<OSS.FIELDNAME
--		MULTIMEDIA-SYSTEM-CONTROL.ResponseMessage.communicationModeResponse
--		"communicationModeResponse">--
--<OSS.DefineName
--		MULTIMEDIA-SYSTEM-CONTROL.ResponseMessage.communicationModeResponse
--		"EM_communicationModeResponse">--
--<OSS.FIELDNAME
--		MULTIMEDIA-SYSTEM-CONTROL.ResponseMessage.conferenceResponse
--		"conferenceResponse">--
--<OSS.DefineName
--		MULTIMEDIA-SYSTEM-CONTROL.ResponseMessage.conferenceResponse
--		"EM_conferenceResponse">--

-- -------------------------------------------------------------- --
--
-- CommandMessage  ::= CHOICE
-- {
--     nonStandard                     NonStandardMessage,
--     maintenanceLoopOffCommand       MaintenanceLoopOffCommand,
--     sendTerminalCapabilitySet       SendTerminalCapabilitySet,
--     encryptionCommand               EncryptionCommand,
--     flowControlCommand              FlowControlCommand,
--     endSessionCommand               EndSessionCommand,
--     miscellaneousCommand            MiscellaneousCommand,
--     ...,
--     communicationModeCommand        CommunicationModeCommand,
--     conferenceCommand               ConferenceCommand
--     h223MultiplexReconfiguration    H223MultiplexReconfiguration
-- }
--
-- -------------------------------------------------------------- --

--<ASN1.PDU
--		MULTIMEDIA-SYSTEM-CONTROL.CommandMessage>--
--<OSS.TYPENAME
--		MULTIMEDIA-SYSTEM-CONTROL.CommandMessage
--		"EmCommandMessage">--
--<OSS.FIELDNAME
--		MULTIMEDIA-SYSTEM-CONTROL.CommandMessage.nonStandard
--		"nonStandard">--
--<OSS.DefineName
--		MULTIMEDIA-SYSTEM-CONTROL.CommandMessage.nonStandard
--		"EM_CommandMessage_nonStandard">--
--<OSS.FIELDNAME
--		MULTIMEDIA-SYSTEM-CONTROL.CommandMessage.maintenanceLoopOffCommand
--		"maintenanceLoopOffCommand">--
--<OSS.DefineName
--		MULTIMEDIA-SYSTEM-CONTROL.CommandMessage.maintenanceLoopOffCommand
--		"EM_maintenanceLoopOffCommand">--
--<OSS.FIELDNAME
--		MULTIMEDIA-SYSTEM-CONTROL.CommandMessage.sendTerminalCapabilitySet
--		"sendTerminalCapabilitySet">--
--<OSS.DefineName
--		MULTIMEDIA-SYSTEM-CONTROL.CommandMessage.sendTerminalCapabilitySet
--		"EM_sendTerminalCapabilitySet">--
--<OSS.FIELDNAME
--		MULTIMEDIA-SYSTEM-CONTROL.CommandMessage.encryptionCommand
--		"encryptionCommand">--
--<OSS.DefineName
--		MULTIMEDIA-SYSTEM-CONTROL.CommandMessage.encryptionCommand
--		"EM_encryptionCommand">--
--<OSS.FIELDNAME
--		MULTIMEDIA-SYSTEM-CONTROL.CommandMessage.flowControlCommand
--		"flowControlCommand">--
--<OSS.DefineName
--		MULTIMEDIA-SYSTEM-CONTROL.CommandMessage.flowControlCommand
--		"EM_flowControlCommand">--
--<OSS.FIELDNAME
--		MULTIMEDIA-SYSTEM-CONTROL.CommandMessage.endSessionCommand
--		"endSessionCommand">--
--<OSS.DefineName
--		MULTIMEDIA-SYSTEM-CONTROL.CommandMessage.endSessionCommand
--		"EM_endSessionCommand">--
--<OSS.FIELDNAME
--		MULTIMEDIA-SYSTEM-CONTROL.CommandMessage.miscellaneousCommand
--		"miscellaneousCommand">--
--<OSS.DefineName
--		MULTIMEDIA-SYSTEM-CONTROL.CommandMessage.miscellaneousCommand
--		"EM_miscellaneousCommand">--
--<OSS.FIELDNAME
--		MULTIMEDIA-SYSTEM-CONTROL.CommandMessage.communicationModeCommand
--		"communicationModeCommand">--
--<OSS.DefineName
--		MULTIMEDIA-SYSTEM-CONTROL.CommandMessage.communicationModeCommand
--		"EM_communicationModeCommand">--
--<OSS.FIELDNAME
--		MULTIMEDIA-SYSTEM-CONTROL.CommandMessage.conferenceCommand
--		"conferenceCommand">--
--<OSS.DefineName
--		MULTIMEDIA-SYSTEM-CONTROL.CommandMessage.conferenceCommand
--		"EM_conferenceCommand">--
--<OSS.FIELDNAME
--		MULTIMEDIA-SYSTEM-CONTROL.CommandMessage.h223MultiplexReconfiguration
--		"h223MultiplexReconfiguration">--
--<OSS.DefineName
--		MULTIMEDIA-SYSTEM-CONTROL.CommandMessage.h223MultiplexReconfiguration
--		"EM_h223MultiplexReconfiguration">--

-- -------------------------------------------------------------- --
--
-- IndicationMessage   ::= CHOICE
-- {
--     nonStandard                     NonStandardMessage,
--     functionNotUnderstood           FunctionNotUnderstood,
--     masterSlaveDeterminationRelease MasterSlaveDeterminationRelease,
--     terminalCapabilitySetRelease    TerminalCapabilitySetRelease,
--     openLogicalChannelConfirm       OpenLogicalChannelConfirm,
--     requestChannelCloseRelease      RequestChannelCloseRelease,
--     multiplexEntrySendRelease       MultiplexEntrySendRelease,
--     requestMultiplexEntryRelease    RequestMultiplexEntryRelease,
--     requestModeRelease              RequestModeRelease,
--     miscellaneousIndication         MiscellaneousIndication,
--     jitterIndication                JitterIndication,
--     h223SkewIndication              H223SkewIndication,
--     newATMVCIndication              NewATMVCIndication,
--     userInput                       UserInputIndication,
--     ...,
--     h2250MaximumSkewIndication      H2250MaximumSkewIndication,
--     mcLocationIndication            MCLocationIndication,
--     conferenceIndication            ConferenceIndication,
--     vendorIdentification            VendorIdentification,
--     functionNotSupported            FunctionNotSupported
-- }
--
-- -------------------------------------------------------------- --

--<ASN1.PDU
--		MULTIMEDIA-SYSTEM-CONTROL.IndicationMessage>--
--<OSS.TYPENAME
--		MULTIMEDIA-SYSTEM-CONTROL.IndicationMessage
--		"EmIndicationMessage">--
--<OSS.FIELDNAME
--		MULTIMEDIA-SYSTEM-CONTROL.IndicationMessage.nonStandard
--		"nonStandard">--
--<OSS.DefineName
--		MULTIMEDIA-SYSTEM-CONTROL.IndicationMessage.nonStandard
--		"EM_IndicationMessage_nonStandard">--
--<OSS.FIELDNAME
--		MULTIMEDIA-SYSTEM-CONTROL.IndicationMessage.functionNotUnderstood
--		"functionNotUnderstood">--
--<OSS.DefineName
--		MULTIMEDIA-SYSTEM-CONTROL.IndicationMessage.functionNotUnderstood
--		"EM_functionNotUnderstood">--
--<OSS.FIELDNAME
--		MULTIMEDIA-SYSTEM-CONTROL.IndicationMessage.masterSlaveDeterminationRelease
--		"masterSlaveDeterminationRelease">--
--<OSS.DefineName
--		MULTIMEDIA-SYSTEM-CONTROL.IndicationMessage.masterSlaveDeterminationRelease
--		"EM_masterSlaveDeterminationRelease">--
--<OSS.FIELDNAME
--		MULTIMEDIA-SYSTEM-CONTROL.IndicationMessage.terminalCapabilitySetRelease
--		"terminalCapabilitySetRelease">--
--<OSS.DefineName
--		MULTIMEDIA-SYSTEM-CONTROL.IndicationMessage.terminalCapabilitySetRelease
--		"EM_terminalCapabilitySetRelease">--
--<OSS.FIELDNAME
--		MULTIMEDIA-SYSTEM-CONTROL.IndicationMessage.openLogicalChannelConfirm
--		"openLogicalChannelConfirm">--
--<OSS.DefineName
--		MULTIMEDIA-SYSTEM-CONTROL.IndicationMessage.openLogicalChannelConfirm
--		"EM_openLogicalChannelConfirm">--
--<OSS.FIELDNAME
--		MULTIMEDIA-SYSTEM-CONTROL.IndicationMessage.requestChannelCloseRelease
--		"requestChannelCloseRelease">--
--<OSS.DefineName
--		MULTIMEDIA-SYSTEM-CONTROL.IndicationMessage.requestChannelCloseRelease
--		"EM_requestChannelCloseRelease">--

--<ASN1.Remove
--		MULTIMEDIA-SYSTEM-CONTROL.IndicationMessage.multiplexEntrySendRelease>--


--<ASN1.Remove
--		MULTIMEDIA-SYSTEM-CONTROL.IndicationMessage.requestMultiplexEntryRelease>--

--<OSS.FIELDNAME
--		MULTIMEDIA-SYSTEM-CONTROL.IndicationMessage.requestModeRelease
--		"requestModeRelease">--
--<OSS.DefineName
--		MULTIMEDIA-SYSTEM-CONTROL.IndicationMessage.requestModeRelease
--		"EM_requestModeRelease">--
--<OSS.FIELDNAME
--		MULTIMEDIA-SYSTEM-CONTROL.IndicationMessage.miscellaneousIndication
--		"miscellaneousIndication">--
--<OSS.DefineName
--		MULTIMEDIA-SYSTEM-CONTROL.IndicationMessage.miscellaneousIndication
--		"EM_miscellaneousIndication">--
--<OSS.FIELDNAME
--		MULTIMEDIA-SYSTEM-CONTROL.IndicationMessage.jitterIndication
--		"jitterIndication">--
--<OSS.DefineName
--		MULTIMEDIA-SYSTEM-CONTROL.IndicationMessage.jitterIndication
--		"EM_jitterIndication">--

--<ASN1.Remove
--		MULTIMEDIA-SYSTEM-CONTROL.IndicationMessage.h223SkewIndication>--

--<ASN1.Remove
--		MULTIMEDIA-SYSTEM-CONTROL.IndicationMessage.newATMVCIndication>--

--<OSS.FIELDNAME
--		MULTIMEDIA-SYSTEM-CONTROL.IndicationMessage.userInput
--		"userInput">--
--<OSS.DefineName
--		MULTIMEDIA-SYSTEM-CONTROL.IndicationMessage.userInput
--		"EM_userInput">--
--<OSS.FIELDNAME
--		MULTIMEDIA-SYSTEM-CONTROL.IndicationMessage.h2250MaximumSkewIndication
--		"h2250MaximumSkewIndication">--
--<OSS.DefineName
--		MULTIMEDIA-SYSTEM-CONTROL.IndicationMessage.h2250MaximumSkewIndication
--		"EM_h2250MaximumSkewIndication">--
--<OSS.FIELDNAME
--		MULTIMEDIA-SYSTEM-CONTROL.IndicationMessage.mcLocationIndication
--		"mcLocationIndication">--
--<OSS.DefineName
--		MULTIMEDIA-SYSTEM-CONTROL.IndicationMessage.mcLocationIndication
--		"EM_mcLocationIndication">--
--<OSS.FIELDNAME
--		MULTIMEDIA-SYSTEM-CONTROL.IndicationMessage.conferenceIndication
--		"conferenceIndication">--
--<OSS.DefineName
--		MULTIMEDIA-SYSTEM-CONTROL.IndicationMessage.conferenceIndication
--		"EM_conferenceIndication">--
--<OSS.FIELDNAME
--		MULTIMEDIA-SYSTEM-CONTROL.IndicationMessage.vendorIdentification
--		"vendorIdentification">--
--<OSS.DefineName
--		MULTIMEDIA-SYSTEM-CONTROL.IndicationMessage.vendorIdentification
--		"EM_vendorIdentification">--
--<OSS.FIELDNAME
--		MULTIMEDIA-SYSTEM-CONTROL.IndicationMessage.functionNotSupported
--		"functionNotSupported">--
--<OSS.DefineName
--		MULTIMEDIA-SYSTEM-CONTROL.IndicationMessage.functionNotSupported
--		"EM_functionNotSupported">--
 
-- -------------------------------------------------------------- --
--
-- SequenceNumber ::= INTEGER(0..255)
--
-- -------------------------------------------------------------- --

--<OSS.TYPENAME
--		MULTIMEDIA-SYSTEM-CONTROL.SequenceNumber
--		"EmSequenceNumber">--

-- ==============================================================
-- Non standard Message definitions
-- ==============================================================

-- -------------------------------------------------------------- --
--
-- NonStandardMessage  ::= SEQUENCE
-- {
--     nonStandardData NonStandardParameter,
--     ...
-- }
--
-- -------------------------------------------------------------- --

--<OSS.TYPENAME
--		MULTIMEDIA-SYSTEM-CONTROL.NonStandardMessage
--		"EmNonStandardMessage">--
--<OSS.FIELDNAME
--		MULTIMEDIA-SYSTEM-CONTROL.NonStandardMessage.nonStandardData
--		"nonStandardData">--

-- -------------------------------------------------------------- --
--  
-- NonStandardParameter    ::= SEQUENCE
-- {
--     nonStandardIdentifier   NonStandardIdentifier,
--     data        OCTET STRING
-- }
--
-- -------------------------------------------------------------- --

--<OSS.TYPENAME
--		MULTIMEDIA-SYSTEM-CONTROL.NonStandardParameter
--		"EmNonStandardParameter">--
--<OSS.FIELDNAME
--		MULTIMEDIA-SYSTEM-CONTROL.NonStandardParameter.nonStandardIdentifier
--		"nonStandardIdentifier">--
--<OSS.FIELDNAME
--		MULTIMEDIA-SYSTEM-CONTROL.NonStandardParameter.data
--		"data">--

-- -------------------------------------------------------------- --
--  
-- NonStandardIdentifier   ::= CHOICE
-- {
--     object      OBJECT IDENTIFIER,
--     h221NonStandard SEQUENCE
--     {
--         t35CountryCode  INTEGER (0..255),
--         t35Extension    INTEGER (0..255),
--         manufacturerCode    INTEGER (0..65535)
--     }
-- }
--
-- -------------------------------------------------------------- --

--<OSS.TYPENAME
--		MULTIMEDIA-SYSTEM-CONTROL.NonStandardIdentifier
--		"EmNonStandardIdentifier">--
--<OSS.FIELDNAME
--		MULTIMEDIA-SYSTEM-CONTROL.NonStandardIdentifier.object
--		"object">--
--<OSS.DefineName
--		MULTIMEDIA-SYSTEM-CONTROL.NonStandardIdentifier.object
--		"EM_object">--
--<OSS.ExtractType
--		MULTIMEDIA-SYSTEM-CONTROL.NonStandardIdentifier.h221NonStandard>--
--<OSS.TYPENAME
--		MULTIMEDIA-SYSTEM-CONTROL.NonStandardIdentifier.h221NonStandard
--		"H221NonStandard">--
--<OSS.FIELDNAME
--		MULTIMEDIA-SYSTEM-CONTROL.NonStandardIdentifier.h221NonStandard
--		"h221NonStandard">--
--<OSS.DefineName
--		MULTIMEDIA-SYSTEM-CONTROL.NonStandardIdentifier.h221NonStandard
--		"EM_h221NonStandard">--
--<OSS.FIELDNAME
--		MULTIMEDIA-SYSTEM-CONTROL.NonStandardIdentifier.h221NonStandard.t35CountryCode
--		"t35CountryCode">--
--<OSS.FIELDNAME
--		MULTIMEDIA-SYSTEM-CONTROL.NonStandardIdentifier.h221NonStandard.t35Extension
--		"t35Extension">--
--<OSS.FIELDNAME
--		MULTIMEDIA-SYSTEM-CONTROL.NonStandardIdentifier.h221NonStandard.manufacturerCode
--		"manufacturerCode">--

-- ==============================================================
-- Master-slave determination definitions
-- ==============================================================

-- -------------------------------------------------------------- --
--
-- MasterSlaveDetermination    ::= SEQUENCE
-- {
--     terminalType    INTEGER (0..255),
--     statusDeterminationNumber   INTEGER (0..16777215),
--     ...
-- }
--
-- -------------------------------------------------------------- --

--<ASN1.PDU
--		MULTIMEDIA-SYSTEM-CONTROL.MasterSlaveDetermination>--
--<OSS.TYPENAME
--		MULTIMEDIA-SYSTEM-CONTROL.MasterSlaveDetermination
--		"EmMasterSlaveDetermination">--
--<OSS.FIELDNAME
--		MULTIMEDIA-SYSTEM-CONTROL.MasterSlaveDetermination.terminalType
--		"terminalType">--
--<OSS.FIELDNAME
--		MULTIMEDIA-SYSTEM-CONTROL.MasterSlaveDetermination.statusDeterminationNumber
--		"statusDeterminationNumber">--

-- -------------------------------------------------------------- --
-- 
-- MasterSlaveDeterminationAck ::= SEQUENCE
-- {
--     decision    CHOICE
--     {
--         master  NULL,
--         slave   NULL
--     },
--     ...
-- }
--
-- -------------------------------------------------------------- --

--<ASN1.PDU
--		MULTIMEDIA-SYSTEM-CONTROL.MasterSlaveDeterminationAck>--
--<OSS.TYPENAME
--		MULTIMEDIA-SYSTEM-CONTROL.MasterSlaveDeterminationAck
--		"EmMasterSlaveDeterminationAck">--
--<OSS.FIELDNAME
--		MULTIMEDIA-SYSTEM-CONTROL.MasterSlaveDeterminationAck.decision
--		"decision">--
--<OSS.ExtractType
--		MULTIMEDIA-SYSTEM-CONTROL.MasterSlaveDeterminationAck.decision>--
--<OSS.TYPENAME
--		MULTIMEDIA-SYSTEM-CONTROL.MasterSlaveDeterminationAck.decision
--		"EmMSDAckDecision">--
--<OSS.FIELDNAME
--		MULTIMEDIA-SYSTEM-CONTROL.MasterSlaveDeterminationAck.decision.master
--		"master">--
--<OSS.DefineName
--		MULTIMEDIA-SYSTEM-CONTROL.MasterSlaveDeterminationAck.decision.master
--		"EM_master">--
--<OSS.FIELDNAME
--		MULTIMEDIA-SYSTEM-CONTROL.MasterSlaveDeterminationAck.decision.slave
--		"slave">--
--<OSS.DefineName
--		MULTIMEDIA-SYSTEM-CONTROL.MasterSlaveDeterminationAck.decision.slave
--		"EM_slave">--

-- -------------------------------------------------------------- --
-- 
-- MasterSlaveDeterminationReject  ::= SEQUENCE
-- {
--     cause       CHOICE
--     {
--         identicalNumbers    NULL,
--         ...
--     },
--     ...
-- }
--
-- -------------------------------------------------------------- --

--<ASN1.PDU
--		MULTIMEDIA-SYSTEM-CONTROL.MasterSlaveDeterminationReject>--
--<OSS.TYPENAME
--		MULTIMEDIA-SYSTEM-CONTROL.MasterSlaveDeterminationReject
--		"EmMasterSlaveDeterminationReject">--
--<OSS.FIELDNAME
--		MULTIMEDIA-SYSTEM-CONTROL.MasterSlaveDeterminationReject.cause
--		"cause">--
--<OSS.ExtractType
--		MULTIMEDIA-SYSTEM-CONTROL.MasterSlaveDeterminationReject.cause>--
--<OSS.TYPENAME
--		MULTIMEDIA-SYSTEM-CONTROL.MasterSlaveDeterminationReject.cause
--		"EmMSDRejectCause">--
--<OSS.FIELDNAME
--		MULTIMEDIA-SYSTEM-CONTROL.MasterSlaveDeterminationReject.cause.identicalNumbers
--		"identicalNumbers">--
--<OSS.DefineName
--		MULTIMEDIA-SYSTEM-CONTROL.MasterSlaveDeterminationReject.cause.identicalNumbers
--		"EM_identicalNumbers">--

-- -------------------------------------------------------------- --
-- 
-- MasterSlaveDeterminationRelease ::= SEQUENCE
-- {
--     ...
-- }
--
-- -------------------------------------------------------------- --

--<OSS.TYPENAME
--		MULTIMEDIA-SYSTEM-CONTROL.MasterSlaveDeterminationRelease
--		"EmMasterSlaveDeterminationRelease">--

-- ==============================================================
-- Capability exchange definitions
-- ==============================================================

-- -------------------------------------------------------------- --
--
-- TerminalCapabilitySet   ::= SEQUENCE
-- {
--     sequenceNumber  SequenceNumber,
--     protocolIdentifier  OBJECT IDENTIFIER,
--     multiplexCapability MultiplexCapability  OPTIONAL,
--     capabilityTable SET  SIZE (1..256) OF CapabilityTableEntry  OPTIONAL,
--     capabilityDescriptors   SET  SIZE (1..256) OF CapabilityDescriptor  OPTIONAL,
--     ...
-- }
--
-- -------------------------------------------------------------- --

--<ASN1.PDU
--		MULTIMEDIA-SYSTEM-CONTROL.TerminalCapabilitySet>--
--<OSS.TYPENAME
--		MULTIMEDIA-SYSTEM-CONTROL.TerminalCapabilitySet
--		"EmTerminalCapabilitySet">--
--<OSS.FIELDNAME
--		MULTIMEDIA-SYSTEM-CONTROL.TerminalCapabilitySet.sequenceNumber
--		"sequenceNumber">--
--<OSS.FIELDNAME
--		MULTIMEDIA-SYSTEM-CONTROL.TerminalCapabilitySet.protocolIdentifier
--		"protocolIdentifier">--
--<OSS.FIELDNAME
--		MULTIMEDIA-SYSTEM-CONTROL.TerminalCapabilitySet.multiplexCapability
--		"multiplexCapability">--
--<OSS.DefineName
--		MULTIMEDIA-SYSTEM-CONTROL.TerminalCapabilitySet.multiplexCapability
--		"EM_multiplexCapability">--
--<OSS.FIELDNAME
--		MULTIMEDIA-SYSTEM-CONTROL.TerminalCapabilitySet.capabilityTable
--		"capabilityTable">--
--<OSS.DefineName
--		MULTIMEDIA-SYSTEM-CONTROL.TerminalCapabilitySet.capabilityTable
--		"EM_capabilityTable">--
--<OSS.FIELDNAME
--		MULTIMEDIA-SYSTEM-CONTROL.TerminalCapabilitySet.capabilityDescriptors
--		"capabilityDescriptors">--
--<OSS.DefineName
--		MULTIMEDIA-SYSTEM-CONTROL.TerminalCapabilitySet.capabilityDescriptors
--		"EM_capabilityDescriptors">--

-- -------------------------------------------------------------- --
-- 
-- CapabilityTableEntry    ::= SEQUENCE
-- {
--     capabilityTableEntryNumber  CapabilityTableEntryNumber,
--     capability  Capability  OPTIONAL
-- }
--
-- -------------------------------------------------------------- --

--<ASN1.PDU
--		MULTIMEDIA-SYSTEM-CONTROL.CapabilityTableEntry>--
--<OSS.TYPENAME
--		MULTIMEDIA-SYSTEM-CONTROL.CapabilityTableEntry
--		"EmCapabilityTableEntry">--
--<OSS.FIELDNAME
--		MULTIMEDIA-SYSTEM-CONTROL.CapabilityTableEntry.capabilityTableEntryNumber
--		"capabilityTableEntryNumber">--
--<OSS.FIELDNAME
--		MULTIMEDIA-SYSTEM-CONTROL.CapabilityTableEntry.capability
--		"capability">--
--<OSS.DefineName
--		MULTIMEDIA-SYSTEM-CONTROL.CapabilityTableEntry.capability
--		"EM_capability">--

-- -------------------------------------------------------------- --
-- 
-- CapabilityDescriptor    ::= SEQUENCE
-- {
--     capabilityDescriptorNumber  CapabilityDescriptorNumber,
--     simultaneousCapabilities    SET  SIZE (1..256) OF AlternativeCapabilitySet OPTIONAL
-- }
--
-- -------------------------------------------------------------- --

--<ASN1.PDU
--		MULTIMEDIA-SYSTEM-CONTROL.CapabilityDescriptor>--
--<OSS.TYPENAME
--		MULTIMEDIA-SYSTEM-CONTROL.CapabilityDescriptor
--		"EmCapabilityDescriptor">--
--<OSS.FIELDNAME
--		MULTIMEDIA-SYSTEM-CONTROL.CapabilityDescriptor.capabilityDescriptorNumber
--		"capabilityDescriptorNumber">--
--<OSS.FIELDNAME
--		MULTIMEDIA-SYSTEM-CONTROL.CapabilityDescriptor.simultaneousCapabilities
--		"simultaneousCapabilities">--
--<OSS.DefineName
--		MULTIMEDIA-SYSTEM-CONTROL.CapabilityDescriptor.simultaneousCapabilities
--		"EM_simultaneousCapabilities">--

-- -------------------------------------------------------------- --
-- AlternativeCapabilitySet    ::= SEQUENCE  SIZE (1..256) OF CapabilityTableEntryNumber
-- -------------------------------------------------------------- --

--<ASN1.PDU
--		MULTIMEDIA-SYSTEM-CONTROL.AlternativeCapabilitySet>--
--<OSS.TYPENAME
--		MULTIMEDIA-SYSTEM-CONTROL.AlternativeCapabilitySet
--		"EmAlternativeCapabilitySet">--

-- -------------------------------------------------------------- --
-- CapabilityTableEntryNumber  ::=INTEGER (1..65535)
-- -------------------------------------------------------------- --

--<OSS.TYPENAME
--		MULTIMEDIA-SYSTEM-CONTROL.CapabilityTableEntryNumber
--		"EmCapabilityTableEntryNumber">--

-- -------------------------------------------------------------- --
-- CapabilityDescriptorNumber  ::=INTEGER (0..255)
-- -------------------------------------------------------------- --

--<OSS.TYPENAME
--		MULTIMEDIA-SYSTEM-CONTROL.CapabilityDescriptorNumber
--		"EmCapabilityDescriptorNumber">--

-- -------------------------------------------------------------- --
-- 
-- TerminalCapabilitySetAck    ::= SEQUENCE
-- {
--     sequenceNumber  SequenceNumber,
--     ...
-- }
-- 
-- -------------------------------------------------------------- --

--<ASN1.PDU
--		MULTIMEDIA-SYSTEM-CONTROL.TerminalCapabilitySetAck>--
--<OSS.TYPENAME
--		MULTIMEDIA-SYSTEM-CONTROL.TerminalCapabilitySetAck
--		"EmTerminalCapabilitySetAck">--
--<OSS.FIELDNAME
--		MULTIMEDIA-SYSTEM-CONTROL.TerminalCapabilitySetAck.sequenceNumber
--		"sequenceNumber">--

-- -------------------------------------------------------------- --
-- 
-- TerminalCapabilitySetReject ::= SEQUENCE
-- {
--     sequenceNumber  SequenceNumber,
--     cause       CHOICE
--     {
--         unspecified NULL,
--         undefinedTableEntryUsed NULL,
--         descriptorCapacityExceeded  NULL,
--         tableEntryCapacityExceeded  CHOICE
--         {
--             highestEntryNumberProcessed CapabilityTableEntryNumber,
--             noneProcessed   NULL
--         },
--         ...
--     },
--     ...
-- }
-- 
-- -------------------------------------------------------------- --

--<ASN1.PDU
--		MULTIMEDIA-SYSTEM-CONTROL.TerminalCapabilitySetReject>--
--<OSS.TYPENAME
--		MULTIMEDIA-SYSTEM-CONTROL.TerminalCapabilitySetReject
--		"EmTerminalCapabilitySetReject">--
--<OSS.FIELDNAME
--		MULTIMEDIA-SYSTEM-CONTROL.TerminalCapabilitySetReject.sequenceNumber
--		"sequenceNumber">--
--<OSS.FIELDNAME
--		MULTIMEDIA-SYSTEM-CONTROL.TerminalCapabilitySetReject.cause
--		"cause">--
--<OSS.ExtractType
--		MULTIMEDIA-SYSTEM-CONTROL.TerminalCapabilitySetReject.cause>--
--<OSS.TYPENAME
--		MULTIMEDIA-SYSTEM-CONTROL.TerminalCapabilitySetReject.cause
--		"EmTermCapRejectCause">--
--<OSS.FIELDNAME
--		MULTIMEDIA-SYSTEM-CONTROL.TerminalCapabilitySetReject.cause.unspecified
--		"unspecified">--
--<OSS.DefineName
--		MULTIMEDIA-SYSTEM-CONTROL.TerminalCapabilitySetReject.cause.unspecified
--		"EM_TermCapRejectCause_unspecified">--
--<OSS.FIELDNAME
--		MULTIMEDIA-SYSTEM-CONTROL.TerminalCapabilitySetReject.cause.undefinedTableEntryUsed
--		"undefinedTableEntryUsed">--
--<OSS.DefineName
--		MULTIMEDIA-SYSTEM-CONTROL.TerminalCapabilitySetReject.cause.undefinedTableEntryUsed
--		"EM_undefinedTableEntryUsed">--
--<OSS.FIELDNAME
--		MULTIMEDIA-SYSTEM-CONTROL.TerminalCapabilitySetReject.cause.descriptorCapacityExceeded
--		"descriptorCapacityExceeded">--
--<OSS.DefineName
--		MULTIMEDIA-SYSTEM-CONTROL.TerminalCapabilitySetReject.cause.descriptorCapacityExceeded
--		"EM_descriptorCapacityExceeded">--
--<OSS.FIELDNAME
--		MULTIMEDIA-SYSTEM-CONTROL.TerminalCapabilitySetReject.cause.tableEntryCapacityExceeded
--		"tableEntryCapacityExceeded">--
--<OSS.DefineName
--		MULTIMEDIA-SYSTEM-CONTROL.TerminalCapabilitySetReject.cause.tableEntryCapacityExceeded
--		"EM_tableEntryCapacityExceeded">--
--<OSS.ExtractType
--		MULTIMEDIA-SYSTEM-CONTROL.TerminalCapabilitySetReject.cause.tableEntryCapacityExceeded>--
--<OSS.TYPENAME
--		MULTIMEDIA-SYSTEM-CONTROL.TerminalCapabilitySetReject.cause.tableEntryCapacityExceeded
--		"EmCapacityExceeded">--
--<OSS.FIELDNAME
--		MULTIMEDIA-SYSTEM-CONTROL.TerminalCapabilitySetReject.cause.tableEntryCapacityExceeded.highestEntryNumberProcessed
--		"highestEntryNumberProcessed">--
--<OSS.DefineName
--		MULTIMEDIA-SYSTEM-CONTROL.TerminalCapabilitySetReject.cause.tableEntryCapacityExceeded.highestEntryNumberProcessed
--		"EM_highestEntryNumberProcessed">--
--<OSS.FIELDNAME
--		MULTIMEDIA-SYSTEM-CONTROL.TerminalCapabilitySetReject.cause.tableEntryCapacityExceeded.noneProcessed
--		"noneProcessed">--
--<OSS.DefineName
--		MULTIMEDIA-SYSTEM-CONTROL.TerminalCapabilitySetReject.cause.tableEntryCapacityExceeded.noneProcessed
--		"EM_noneProcessed">--

-- -------------------------------------------------------------- --
-- 
-- TerminalCapabilitySetRelease    ::= SEQUENCE
-- {
--     ...
-- }
--
-- -------------------------------------------------------------- --

--<OSS.TYPENAME
--		MULTIMEDIA-SYSTEM-CONTROL.TerminalCapabilitySetRelease
--		"EmTerminalCapabilitySetRelease">--

-- ==============================================================
-- Capability exchange definitions: top level capability description
-- ==============================================================

-- -------------------------------------------------------------- --
-- 
-- Capability      ::= CHOICE
-- {
--     nonStandard NonStandardParameter,
-- 
--     receiveVideoCapability                      VideoCapability,
--     transmitVideoCapability                     VideoCapability,
--     receiveAndTransmitVideoCapability           VideoCapability,
-- 
--     receiveAudioCapability                      AudioCapability,
--     transmitAudioCapability                     AudioCapability,
--     receiveAndTransmitAudioCapability           AudioCapability,
-- 
--     receiveDataApplicationCapability            DataApplicationCapability,
--     transmitDataApplicationCapability           DataApplicationCapability,
--     receiveAndTransmitDataApplicationCapability DataApplicationCapability,
-- 
--     h233EncryptionTransmitCapability            BOOLEAN,
--     h233EncryptionReceiveCapability             SEQUENCE
--     {
--         h233IVResponseTime  INTEGER (0..255),
--         ...
--     },
--     ...,
--     conferenceCapability                        ConferenceCapability
--     h235SecurityCapability                      H235SecurityCapability,
--     maxPendingReplacementFor                    INTEGER(0..255),
--  
--     receiveUserInputCapability                  UserInputCapability,
--     transmitUserInputCapability                 UserInputCapability,
--     receiveAndTransmitUserInputCapability       UserInputCapability
-- 
-- }
--
-- -------------------------------------------------------------- --

--<ASN1.PDU
--		MULTIMEDIA-SYSTEM-CONTROL.Capability>--
--<OSS.TYPENAME
--		MULTIMEDIA-SYSTEM-CONTROL.Capability
--		"EmCapability">--
--<OSS.FIELDNAME
--	MULTIMEDIA-SYSTEM-CONTROL.Capability.nonStandard
--	"nonStandard">--
--<OSS.DefineName
--	MULTIMEDIA-SYSTEM-CONTROL.Capability.nonStandard
--	"EM_Capability_nonStandard">--
--<OSS.FIELDNAME
--	MULTIMEDIA-SYSTEM-CONTROL.Capability.receiveVideoCapability
--	"receiveVideoCapability">--
--<OSS.DefineName
--	MULTIMEDIA-SYSTEM-CONTROL.Capability.receiveVideoCapability
--	"EM_receiveVideoCapability">--
--<OSS.FIELDNAME
--	MULTIMEDIA-SYSTEM-CONTROL.Capability.transmitVideoCapability
--	"transmitVideoCapability">--
--<OSS.DefineName
--	MULTIMEDIA-SYSTEM-CONTROL.Capability.transmitVideoCapability
--	"EM_transmitVideoCapability">--
--<OSS.FIELDNAME
--	MULTIMEDIA-SYSTEM-CONTROL.Capability.receiveAndTransmitVideoCapability
--	"receiveAndTransmitVideoCapability">--
--<OSS.DefineName
--	MULTIMEDIA-SYSTEM-CONTROL.Capability.receiveAndTransmitVideoCapability
--	"EM_receiveAndTransmitVideoCapability">--
--<OSS.FIELDNAME
--	MULTIMEDIA-SYSTEM-CONTROL.Capability.receiveAudioCapability
--	"receiveAudioCapability">--
--<OSS.DefineName
--	MULTIMEDIA-SYSTEM-CONTROL.Capability.receiveAudioCapability
--	"EM_receiveAudioCapability">--
--<OSS.FIELDNAME
--	MULTIMEDIA-SYSTEM-CONTROL.Capability.transmitAudioCapability
--	"transmitAudioCapability">--
--<OSS.DefineName
--	MULTIMEDIA-SYSTEM-CONTROL.Capability.transmitAudioCapability
--	"EM_transmitAudioCapability">--
--<OSS.FIELDNAME
--	MULTIMEDIA-SYSTEM-CONTROL.Capability.receiveAndTransmitAudioCapability
--	"receiveAndTransmitAudioCapability">--
--<OSS.DefineName
--	MULTIMEDIA-SYSTEM-CONTROL.Capability.receiveAndTransmitAudioCapability
--	"EM_receiveAndTransmitAudioCapability">--
--<OSS.FIELDNAME
--	MULTIMEDIA-SYSTEM-CONTROL.Capability.receiveDataApplicationCapability
--	"receiveDataApplicationCapability">--
--<OSS.DefineName
--	MULTIMEDIA-SYSTEM-CONTROL.Capability.receiveDataApplicationCapability
--	"EM_receiveDataApplicationCapability">--
--<OSS.FIELDNAME
--	MULTIMEDIA-SYSTEM-CONTROL.Capability.transmitDataApplicationCapability
--	"transmitDataApplicationCapability">--
--<OSS.DefineName
--	MULTIMEDIA-SYSTEM-CONTROL.Capability.transmitDataApplicationCapability
--	"EM_transmitDataApplicationCapability">--
--<OSS.FIELDNAME
--	MULTIMEDIA-SYSTEM-CONTROL.Capability.receiveAndTransmitDataApplicationCapability
--	"receiveAndTransmitDataApplicationCapability">--
--<OSS.DefineName
--	MULTIMEDIA-SYSTEM-CONTROL.Capability.receiveAndTransmitDataApplicationCapability
--	"EM_receiveAndTransmitDataApplicationCapability">--

--<ASN1.Remove
--	MULTIMEDIA-SYSTEM-CONTROL.Capability.h233EncryptionTransmitCapability>--

--<ASN1.Remove
--	MULTIMEDIA-SYSTEM-CONTROL.Capability.h233EncryptionReceiveCapability>--

--<OSS.FIELDNAME
--	MULTIMEDIA-SYSTEM-CONTROL.Capability.conferenceCapability
--	"conferenceCapability">--
--<OSS.DefineName
--	MULTIMEDIA-SYSTEM-CONTROL.Capability.conferenceCapability
--	"EM_conferenceCapability">--
--<OSS.FIELDNAME
--	MULTIMEDIA-SYSTEM-CONTROL.Capability.h235SecurityCapability
--	"h235SecurityCapability">--
--<OSS.DefineName
--	MULTIMEDIA-SYSTEM-CONTROL.Capability.h235SecurityCapability
--	"EM_h235SecurityCapability">--
--<OSS.FIELDNAME
--	MULTIMEDIA-SYSTEM-CONTROL.Capability.maxPendingReplacementFor
--	"maxPendingReplacementFor">--
--<OSS.DefineName
--	MULTIMEDIA-SYSTEM-CONTROL.Capability.maxPendingReplacementFor
--	"EM_maxPendingReplacementFor">--
--<OSS.FIELDNAME
--	MULTIMEDIA-SYSTEM-CONTROL.Capability.receiveUserInputCapability
--	"receiveUserInputCapability">--
--<OSS.DefineName
--	MULTIMEDIA-SYSTEM-CONTROL.Capability.receiveUserInputCapability
--	"EM_receiveUserInputCapability">--
--<OSS.FIELDNAME
--	MULTIMEDIA-SYSTEM-CONTROL.Capability.transmitUserInputCapability
--	"transmitUserInputCapability">--
--<OSS.DefineName
--	MULTIMEDIA-SYSTEM-CONTROL.Capability.transmitUserInputCapability
--	"EM_transmitUserInputCapability">--
--<OSS.FIELDNAME
--	MULTIMEDIA-SYSTEM-CONTROL.Capability.receiveAndTransmitUserInputCapability
--	"receiveAndTransmitUserInputCapability">--
--<OSS.DefineName
--	MULTIMEDIA-SYSTEM-CONTROL.Capability.receiveAndTransmitUserInputCapability
--	"EM_receiveAndTransmitUserInputCapability">--

-- -------------------------------------------------------------- --
-- 
-- H235SecurityCapability  ::=SEQUENCE
-- {
--     encryptionAuthenticationAndIntegrity    EncryptionAuthenticationAndIntegrity,
--  
--     mediaCapability                         CapabilityTableEntryNumber,
--     ...
-- }
--
-- -------------------------------------------------------------- --

--<ASN1.PDU
--		MULTIMEDIA-SYSTEM-CONTROL.H235SecurityCapability>--
--<OSS.TYPENAME
--		MULTIMEDIA-SYSTEM-CONTROL.H235SecurityCapability
--		"EmH235SecurityCapability">--
--<OSS.FIELDNAME
--	MULTIMEDIA-SYSTEM-CONTROL.H235SecurityCapability.encryptionAuthenticationAndIntegrity
--	"encryptionAuthenticationAndIntegrity">--
--<OSS.FIELDNAME
--	MULTIMEDIA-SYSTEM-CONTROL.H235SecurityCapability.mediaCapability
--	"mediaCapability">--

-- ==============================================================
-- Capability exchange definitions: Multiplex capabilities
-- ==============================================================

-- -------------------------------------------------------------- --
--
-- MultiplexCapability ::= CHOICE
-- {
--     nonStandard         NonStandardParameter,
--     h222Capability      H222Capability,
--     h223Capability      H223Capability,
--     v76Capability       V76Capability,
--     ...,
--     h2250Capability     H2250Capability,
-- 
-- }
--
-- -------------------------------------------------------------- --

--<ASN1.PDU
--		MULTIMEDIA-SYSTEM-CONTROL.MultiplexCapability>--
--<OSS.TYPENAME
--		MULTIMEDIA-SYSTEM-CONTROL.MultiplexCapability
--		"EmMultiplexCapability">--
--<OSS.FIELDNAME
--	MULTIMEDIA-SYSTEM-CONTROL.MultiplexCapability.nonStandard
--	"nonStandard">--
--<OSS.DefineName
--	MULTIMEDIA-SYSTEM-CONTROL.MultiplexCapability.nonStandard
--	"EM_MultiplexCapability_nonStandard">--

--<ASN1.Remove
--	MULTIMEDIA-SYSTEM-CONTROL.MultiplexCapability.h222Capability>--

--<ASN1.Remove
--	MULTIMEDIA-SYSTEM-CONTROL.MultiplexCapability.h223Capability>--

--<ASN1.Remove
--	MULTIMEDIA-SYSTEM-CONTROL.MultiplexCapability.v76Capability>--

--<OSS.FIELDNAME
--	MULTIMEDIA-SYSTEM-CONTROL.MultiplexCapability.h2250Capability
--	"h2250Capability">--
--<OSS.DefineName
--	MULTIMEDIA-SYSTEM-CONTROL.MultiplexCapability.h2250Capability
--	"EM_h2250Capability">--

-- -------------------------------------------------------------- --
-- 
-- H222Capability  ::= SEQUENCE
-- {
--     numberOfVCs     INTEGER (1..256),
--     vcCapability    SET  OF VCCapability,
--     ...
-- }
--
-- -------------------------------------------------------------- --

--<ASN1.Remove
--		MULTIMEDIA-SYSTEM-CONTROL.H222Capability>--

-- -------------------------------------------------------------- --
-- 
-- VCCapability    ::= SEQUENCE
-- {
--     aal1        SEQUENCE
--     {
--         nullClockRecovery       BOOLEAN,
--         srtsClockRecovery       BOOLEAN,
--         adaptiveClockRecovery   BOOLEAN,
--         nullErrorCorrection     BOOLEAN,
--         longInterleaver         BOOLEAN,
--         shortInterleaver        BOOLEAN,
--         errorCorrectionOnly     BOOLEAN,
--         structuredDataTransfer  BOOLEAN,
--         partiallyFilledCells    BOOLEAN,
--         ...
--     }  OPTIONAL,
--     aal5        SEQUENCE
--     {
--         forwardMaximumSDUSize   INTEGER (0..65535),
--         backwardMaximumSDUSize  INTEGER (0..65535),
--         ...
--     }  OPTIONAL,
--     transportStream     BOOLEAN,
--     programStream       BOOLEAN,
--     availableBitRates   SEQUENCE
--     {
--         type    CHOICE
--         {
--             singleBitRate   INTEGER (1..65535),
--             rangeOfBitRates SEQUENCE
--             {
--                 lowerBitRate    INTEGER (1..65535),
--                 higherBitRate   INTEGER (1..65535)
--             }
--         },
--         ...
--     },
--     ...
-- }
-- 
-- -------------------------------------------------------------- --

--<ASN1.Remove
--		MULTIMEDIA-SYSTEM-CONTROL.VCCapability>--

-- -------------------------------------------------------------- --
--
-- H223Capability  ::= SEQUENCE
-- {
--     transportWithI-frames   BOOLEAN,
-- 
--     videoWithAL1            BOOLEAN,
--     videoWithAL2            BOOLEAN,
--     videoWithAL3            BOOLEAN,
--     audioWithAL1            BOOLEAN,
--     audioWithAL2            BOOLEAN,
--     audioWithAL3            BOOLEAN,
--     dataWithAL1             BOOLEAN,
--     dataWithAL2             BOOLEAN,
--     dataWithAL3             BOOLEAN,
-- 
--     maximumAl2SDUSize       INTEGER (0..65535),
--     maximumAl3SDUSize       INTEGER (0..65535),
-- 
--     maximumDelayJitter      INTEGER (0..1023),
-- 
--     h223MultiplexTableCapability    CHOICE
--     {
--         basic   NULL,
--         enhanced    SEQUENCE
--         {
--             maximumNestingDepth         INTEGER (1..15),
--             maximumElementListSize      INTEGER (2..255),
--             maximumSubElementListSize   INTEGER (2..255),
--             ...
--         }
--     },
--     ...,
--     maxMUXPDUSizeCapability             BOOLEAN,
--     nsrpSupport                         BOOLEAN,
--     mobileOperationTransmitCapability   SEQUENCE
--     {
--         modeChangeCapability    BOOLEAN,
--         h223AnnexA              BOOLEAN,
--         h223AnnexADoubleFlag    BOOLEAN,
--         h223AnnexB              BOOLEAN,
--         h223AnnexBwithHeader    BOOLEAN,
--         ...
--     } OPTIONAL,
--     h223AnnexCCapability    H223AnnexCCapability OPTIONAL
-- 
-- }
-- 
-- -------------------------------------------------------------- --

--<ASN1.Remove
--		MULTIMEDIA-SYSTEM-CONTROL.H223Capability>--

-- -------------------------------------------------------------- --
--
-- H223AnnexCCapability    ::= SEQUENCE
-- {
--     videoWithAL1M       BOOLEAN,
--     videoWithAL2M       BOOLEAN,
--     videoWithAL3M       BOOLEAN,
--     audioWithAL1M       BOOLEAN,
--     audioWithAL2M       BOOLEAN,
--     audioWithAL3M       BOOLEAN,
--     dataWithAL1M        BOOLEAN,
--     dataWithAL2M        BOOLEAN,
--     dataWithAL3M        BOOLEAN,
--     alpduInterleaving   BOOLEAN,
-- 
--     maximumAL1MPDUSize  INTEGER(0..65535),
--     maximumAL2MSDUSize  INTEGER(0..65535),
--     maximumAL3MSDUSize  INTEGER(0..65535),
--     ...
-- }
--
-- -------------------------------------------------------------- --

--<ASN1.Remove
--		MULTIMEDIA-SYSTEM-CONTROL.H223AnnexCCapability>--

-- -------------------------------------------------------------- --
--
-- V76Capability   ::= SEQUENCE
-- {
--     suspendResumeCapabilitywAddress     BOOLEAN,
--     suspendResumeCapabilitywoAddress    BOOLEAN,
--     rejCapability                       BOOLEAN,
--     sREJCapability                      BOOLEAN,
--     mREJCapability                      BOOLEAN,
--     crc8bitCapability                   BOOLEAN,
--     crc16bitCapability                  BOOLEAN,
--     crc32bitCapability                  BOOLEAN,
--     uihCapability                       BOOLEAN,
--     numOfDLCS                           INTEGER (2..8191),
--     twoOctetAddressFieldCapability      BOOLEAN,
--     loopBackTestCapability              BOOLEAN,
--     n401Capability                      INTEGER (1..4095),
--     maxWindowSizeCapability             INTEGER (1..127),
--     v75Capability                       V75Capability,
--     ...
-- }
-- 
-- -------------------------------------------------------------- --

--<ASN1.Remove
--		MULTIMEDIA-SYSTEM-CONTROL.V76Capability>--

-- -------------------------------------------------------------- --
--
-- V75Capability ::= SEQUENCE
-- {
--     audioHeader BOOLEAN,
--     ...
-- }
-- 
-- -------------------------------------------------------------- --

--<ASN1.Remove
--		MULTIMEDIA-SYSTEM-CONTROL.V75Capability>--

-- -------------------------------------------------------------- --
--
-- H2250Capability ::= SEQUENCE
-- {
--     maximumAudioDelayJitter                 INTEGER(0..1023),
--     receiveMultipointCapability             MultipointCapability,
--     transmitMultipointCapability            MultipointCapability,
--     receiveAndTransmitMultipointCapability  MultipointCapability,
--     mcCapability    SEQUENCE
--     {
--         centralizedConferenceMC     BOOLEAN,
--         decentralizedConferenceMC   BOOLEAN,
--         ...
--     },
--     rtcpVideoControlCapability      BOOLEAN,
--     mediaPacketizationCapability    MediaPacketizationCapability,
--     ...,
--     transportCapability                     TransportCapability OPTIONAL,
--     redundancyEncodingCapability            SEQUENCE SIZE(1..256) OF RedundancyEncodingCapability OPTIONAL,
--     logicalChannelSwitchingCapability       BOOLEAN,
--     t120DynamicPortCapability               BOOLEAN
-- }
-- 
-- -------------------------------------------------------------- --

--<ASN1.PDU
--		MULTIMEDIA-SYSTEM-CONTROL.H2250Capability>--
--<OSS.TYPENAME
--		MULTIMEDIA-SYSTEM-CONTROL.H2250Capability
--		"EmH2250Capability">--
--<OSS.FIELDNAME
--		MULTIMEDIA-SYSTEM-CONTROL.H2250Capability.maximumAudioDelayJitter
--		"maximumAudioDelayJitter">--
--<OSS.FIELDNAME
--		MULTIMEDIA-SYSTEM-CONTROL.H2250Capability.receiveMultipointCapability
--		"receiveMultipointCapability">--
--<OSS.FIELDNAME
--		MULTIMEDIA-SYSTEM-CONTROL.H2250Capability.transmitMultipointCapability
--		"transmitMultipointCapability">--
--<OSS.FIELDNAME
--		MULTIMEDIA-SYSTEM-CONTROL.H2250Capability.receiveAndTransmitMultipointCapability
--		"receiveAndTransmitMultipointCapability">--
--<OSS.InlineType
--		MULTIMEDIA-SYSTEM-CONTROL.H2250Capability.mcCapability>--
--<OSS.TYPENAME
--		MULTIMEDIA-SYSTEM-CONTROL.H2250Capability.mcCapability
--		"EmMCCapability">--
--<OSS.FIELDNAME
--		MULTIMEDIA-SYSTEM-CONTROL.H2250Capability.mcCapability
--		"mcCapability">--
--<OSS.FIELDNAME
--		MULTIMEDIA-SYSTEM-CONTROL.H2250Capability.mcCapability.centralizedConferenceMC
--		"centralizedConferenceMC">--
--<OSS.FIELDNAME
--		MULTIMEDIA-SYSTEM-CONTROL.H2250Capability.mcCapability.decentralizedConferenceMC
--		"decentralizedConferenceMC">--
--<OSS.FIELDNAME
--		MULTIMEDIA-SYSTEM-CONTROL.H2250Capability.rtcpVideoControlCapability
--		"rtcpVideoControlCapability">--
--<OSS.FIELDNAME
--		MULTIMEDIA-SYSTEM-CONTROL.H2250Capability.mediaPacketizationCapability
--		"mediaPacketizationCapability">--
--<OSS.FIELDNAME
--		MULTIMEDIA-SYSTEM-CONTROL.H2250Capability.transportCapability
--		"transportCapability">--
--<OSS.DefineName
--		MULTIMEDIA-SYSTEM-CONTROL.H2250Capability.transportCapability
--		"EM_transportCapability">--
--<OSS.FIELDNAME
--		MULTIMEDIA-SYSTEM-CONTROL.H2250Capability.redundancyEncodingCapability
--		"redundancyEncodingCapability">--
--<OSS.DefineName
--		MULTIMEDIA-SYSTEM-CONTROL.H2250Capability.redundancyEncodingCapability
--		"EM_redundancyEncodingCapability">--
--<OSS.FIELDNAME
--		MULTIMEDIA-SYSTEM-CONTROL.H2250Capability.logicalChannelSwitchingCapability
--		"logicalChannelSwitchingCapability">--
--<OSS.DefineName
--		MULTIMEDIA-SYSTEM-CONTROL.H2250Capability.logicalChannelSwitchingCapability
--		"EM_logicalChannelSwitchingCapability">--
--<OSS.FIELDNAME
--		MULTIMEDIA-SYSTEM-CONTROL.H2250Capability.t120DynamicPortCapability
--		"t120DynamicPortCapability">--
--<OSS.DefineName
--		MULTIMEDIA-SYSTEM-CONTROL.H2250Capability.t120DynamicPortCapability
--		"EM_t120DynamicPortCapability">--

-- -------------------------------------------------------------- --
-- 
-- MediaPacketizationCapability    ::= SEQUENCE
-- {
--     h261aVideoPacketization BOOLEAN,
--     ...,
--     rtpPayloadType              SEQUENCE SIZE(1..256) OF RTPPayloadType OPTIONAL
-- }
-- 
-- -------------------------------------------------------------- --

--<ASN1.PDU
--		MULTIMEDIA-SYSTEM-CONTROL.MediaPacketizationCapability>--
--<OSS.TYPENAME
--		MULTIMEDIA-SYSTEM-CONTROL.MediaPacketizationCapability
--		"EmMediaPacketizationCapability">--
--<OSS.FIELDNAME
--		MULTIMEDIA-SYSTEM-CONTROL.MediaPacketizationCapability.h261aVideoPacketization
--		"h261aVideoPacketization">--
--<OSS.FIELDNAME
--		MULTIMEDIA-SYSTEM-CONTROL.MediaPacketizationCapability.rtpPayloadType
--		"rtpPayloadType">--
--<OSS.DefineName
--		MULTIMEDIA-SYSTEM-CONTROL.MediaPacketizationCapability.rtpPayloadType
--		"EM_rtpPayloadType">--

-- -------------------------------------------------------------- --
-- 
-- RSVPParameters ::= SEQUENCE
-- {
--     qosMode     QOSMode OPTIONAL,
--     tokenRate   INTEGER(1..4294967295) OPTIONAL,
--     bucketSize  INTEGER(1..4294967295) OPTIONAL,
--     peakRate    INTEGER(1..4294967295) OPTIONAL,
--     minPoliced  INTEGER(1..4294967295) OPTIONAL,
--     maxPktSize  INTEGER(1..4294967295) OPTIONAL,
--     ...
-- }
-- 
-- -------------------------------------------------------------- --

--<ASN1.PDU
--		MULTIMEDIA-SYSTEM-CONTROL.RSVPParameters>--
--<OSS.TYPENAME
--		MULTIMEDIA-SYSTEM-CONTROL.RSVPParameters
--		"EmRSVPParameters">--
--<OSS.FIELDNAME
--		MULTIMEDIA-SYSTEM-CONTROL.RSVPParameters.qosMode
--		"qosMode">--
--<OSS.DefineName
--		MULTIMEDIA-SYSTEM-CONTROL.RSVPParameters.qosMode
--		"EM_qosMode">--
--<OSS.FIELDNAME
--		MULTIMEDIA-SYSTEM-CONTROL.RSVPParameters.tokenRate
--		"tokenRate">--
--<OSS.DefineName
--		MULTIMEDIA-SYSTEM-CONTROL.RSVPParameters.tokenRate
--		"EM_tokenRate">--
--<OSS.FIELDNAME
--		MULTIMEDIA-SYSTEM-CONTROL.RSVPParameters.bucketSize
--		"bucketSize">--
--<OSS.DefineName
--		MULTIMEDIA-SYSTEM-CONTROL.RSVPParameters.bucketSize
--		"EM_bucketSize">--
--<OSS.FIELDNAME
--		MULTIMEDIA-SYSTEM-CONTROL.RSVPParameters.peakRate
--		"peakRate">--
--<OSS.DefineName
--		MULTIMEDIA-SYSTEM-CONTROL.RSVPParameters.peakRate
--		"EM_peakRate">--
--<OSS.FIELDNAME
--		MULTIMEDIA-SYSTEM-CONTROL.RSVPParameters.minPoliced
--		"minPoliced">--
--<OSS.DefineName
--		MULTIMEDIA-SYSTEM-CONTROL.RSVPParameters.minPoliced
--		"EM_minPoliced">--
--<OSS.FIELDNAME
--		MULTIMEDIA-SYSTEM-CONTROL.RSVPParameters.maxPktSize
--		"maxPktSize">--
--<OSS.DefineName
--		MULTIMEDIA-SYSTEM-CONTROL.RSVPParameters.maxPktSize
--		"EM_maxPktSize">--

-- -------------------------------------------------------------- --
-- 
-- QOSMode ::= CHOICE
-- {
--     guaranteedQOS   NULL,
--     controlledLoad  NULL,
--     ...
-- }
-- 
-- -------------------------------------------------------------- --

--<ASN1.PDU
--		MULTIMEDIA-SYSTEM-CONTROL.QOSMode>--
--<OSS.TYPENAME
--		MULTIMEDIA-SYSTEM-CONTROL.QOSMode
--		"EmQOSMode">--
--<OSS.FIELDNAME
--		MULTIMEDIA-SYSTEM-CONTROL.QOSMode.guaranteedQOS
--		"guaranteedQOS">--
--<OSS.DefineName
--		MULTIMEDIA-SYSTEM-CONTROL.QOSMode.guaranteedQOS
--		"EM_guaranteedQOS">--
--<OSS.FIELDNAME
--		MULTIMEDIA-SYSTEM-CONTROL.QOSMode.controlledLoad
--		"controlledLoad">--
--<OSS.DefineName
--		MULTIMEDIA-SYSTEM-CONTROL.QOSMode.controlledLoad
--		"EM_controlledLoad">--

-- -------------------------------------------------------------- --
-- 
-- ATMParameters ::= SEQUENCE
-- {
--     maxNTUSize      INTEGER(0..65535),
--     atmUBR          BOOLEAN,
--     atmrtVBR        BOOLEAN,
--     atmnrtVBR       BOOLEAN,
--     atmABR          BOOLEAN,
--     atmCBR          BOOLEAN,
--     ...
-- }
-- 
-- -------------------------------------------------------------- --

--<ASN1.PDU
--		MULTIMEDIA-SYSTEM-CONTROL.ATMParameters>--
--<OSS.TYPENAME
--		MULTIMEDIA-SYSTEM-CONTROL.ATMParameters
--		"EmATMParameters">--
--<OSS.FIELDNAME
--		MULTIMEDIA-SYSTEM-CONTROL.ATMParameters.maxNTUSize
--		"maxNTUSize">--
--<OSS.FIELDNAME
--		MULTIMEDIA-SYSTEM-CONTROL.ATMParameters.atmUBR
--		"atmUBR">--
--<OSS.FIELDNAME
--		MULTIMEDIA-SYSTEM-CONTROL.ATMParameters.atmrtVBR
--		"atmrtVBR">--
--<OSS.FIELDNAME
--		MULTIMEDIA-SYSTEM-CONTROL.ATMParameters.atmnrtVBR
--		"atmnrtVBR">--
--<OSS.FIELDNAME
--		MULTIMEDIA-SYSTEM-CONTROL.ATMParameters.atmABR
--		"atmABR">--
--<OSS.FIELDNAME
--		MULTIMEDIA-SYSTEM-CONTROL.ATMParameters.atmCBR
--		"atmCBR">--

-- -------------------------------------------------------------- --
-- 
-- QOSCapability ::= SEQUENCE
-- {
--     nonStandardData NonStandardParameter OPTIONAL,
--     rsvpParameters  RSVPParameters OPTIONAL,
--     atmParameters   ATMParameters OPTIONAL,
--     ...
-- }
-- 
-- -------------------------------------------------------------- --

--<ASN1.PDU
--		MULTIMEDIA-SYSTEM-CONTROL.QOSCapability>--
--<OSS.TYPENAME
--		MULTIMEDIA-SYSTEM-CONTROL.QOSCapability
--		"EmQOSCapability">--
--<OSS.FIELDNAME
--		MULTIMEDIA-SYSTEM-CONTROL.QOSCapability.nonStandardData
--		"nonStandardData">--
--<OSS.DefineName
--		MULTIMEDIA-SYSTEM-CONTROL.QOSCapability.nonStandardData
--		"EM_QOSCapability_nonStandardData">--
--<OSS.FIELDNAME
--		MULTIMEDIA-SYSTEM-CONTROL.QOSCapability.rsvpParameters
--		"rsvpParameters">--
--<OSS.DefineName
--		MULTIMEDIA-SYSTEM-CONTROL.QOSCapability.rsvpParameters
--		"EM_rsvpParameters">--
--<OSS.FIELDNAME
--		MULTIMEDIA-SYSTEM-CONTROL.QOSCapability.atmParameters
--		"atmParameters">--
--<OSS.DefineName
--		MULTIMEDIA-SYSTEM-CONTROL.QOSCapability.atmParameters
--		"EM_atmParameters">--

-- -------------------------------------------------------------- --
-- 
-- MediaTransportType ::= CHOICE
-- {
--     ip-UDP          NULL,
--     ip-TCP          NULL,
--     atm-AAL5-UNIDIR NULL,
--     atm-AAL5-BIDIR  NULL,
--     ...
-- }
-- 
-- -------------------------------------------------------------- --

--<ASN1.PDU
--		MULTIMEDIA-SYSTEM-CONTROL.MediaTransportType>--
--<OSS.TYPENAME
--		MULTIMEDIA-SYSTEM-CONTROL.MediaTransportType
--		"EmMediaTransportType">--
--<OSS.FIELDNAME
--		MULTIMEDIA-SYSTEM-CONTROL.MediaTransportType.ip-UDP
--		"ip_UDP">--
--<OSS.DefineName
--		MULTIMEDIA-SYSTEM-CONTROL.MediaTransportType.ip-UDP
--		"EM_ip_UDP">--
--<OSS.FIELDNAME
--		MULTIMEDIA-SYSTEM-CONTROL.MediaTransportType.ip-TCP
--		"ip_TCP">--
--<OSS.DefineName
--		MULTIMEDIA-SYSTEM-CONTROL.MediaTransportType.ip-TCP
--		"EM_ip_TCP">--
--<OSS.FIELDNAME
--		MULTIMEDIA-SYSTEM-CONTROL.MediaTransportType.atm-AAL5-UNIDIR
--		"atm_AAL5_UNIDIR">--
--<OSS.DefineName
--		MULTIMEDIA-SYSTEM-CONTROL.MediaTransportType.atm-AAL5-UNIDIR
--		"EM_atm_AAL5_UNIDIR">--
--<OSS.FIELDNAME
--		MULTIMEDIA-SYSTEM-CONTROL.MediaTransportType.atm-AAL5-BIDIR
--		"atm_AAL5_BIDIR">--
--<OSS.DefineName
--		MULTIMEDIA-SYSTEM-CONTROL.MediaTransportType.atm-AAL5-BIDIR
--		"EM_atm_AAL5_BIDIR">--

-- -------------------------------------------------------------- --
-- 
-- MediaChannelCapability ::= SEQUENCE
-- {
--     mediaTransport  MediaTransportType  OPTIONAL,
--     ...
-- }
-- 
-- -------------------------------------------------------------- --

--<ASN1.PDU
--		MULTIMEDIA-SYSTEM-CONTROL.MediaChannelCapability>--
--<OSS.TYPENAME
--		MULTIMEDIA-SYSTEM-CONTROL.MediaChannelCapability
--		"EmMediaChannelCapability">--
--<OSS.FIELDNAME
--		MULTIMEDIA-SYSTEM-CONTROL.MediaChannelCapability.mediaTransport
--		"mediaTransport">--
--<OSS.DefineName
--		MULTIMEDIA-SYSTEM-CONTROL.MediaChannelCapability.mediaTransport
--		"EM_mediaTransport">--

-- -------------------------------------------------------------- --
--
-- TransportCapability ::= SEQUENCE
-- {
--     nonStandard                 NonStandardParameter OPTIONAL,
--     qOSCapabilities             SEQUENCE SIZE(1..256) OF QOSCapability OPTIONAL,
--     mediaChannelCapabilities    SEQUENCE SIZE(1..256) OF MediaChannelCapability OPTIONAL,
--     ...
-- }
-- 
-- -------------------------------------------------------------- --

--<ASN1.PDU
--		MULTIMEDIA-SYSTEM-CONTROL.TransportCapability>--
--<OSS.TYPENAME
--		MULTIMEDIA-SYSTEM-CONTROL.TransportCapability
--		"EmTransportCapability">--
--<OSS.FIELDNAME
--		MULTIMEDIA-SYSTEM-CONTROL.TransportCapability.nonStandard
--		"nonStandard">--
--<OSS.DefineName
--		MULTIMEDIA-SYSTEM-CONTROL.TransportCapability.nonStandard
--		"EM_TransportCapability_nonStandard">--
--<OSS.FIELDNAME
--		MULTIMEDIA-SYSTEM-CONTROL.TransportCapability.qOSCapabilities
--		"qOSCapabilities">--
--<OSS.DefineName
--		MULTIMEDIA-SYSTEM-CONTROL.TransportCapability.qOSCapabilities
--		"EM_qOSCapabilities">--
--<OSS.FIELDNAME
--		MULTIMEDIA-SYSTEM-CONTROL.TransportCapability.mediaChannelCapabilities
--		"mediaChannelCapabilities">--
--<OSS.DefineName
--		MULTIMEDIA-SYSTEM-CONTROL.TransportCapability.mediaChannelCapabilities
--		"EM_mediaChannelCapabilities">--

-- -------------------------------------------------------------- --
--
-- RedundancyEncodingCapability ::= SEQUENCE
-- {
--     redundancyEncodingMethod    RedundancyEncodingMethod,
--     primaryEncoding             CapabilityTableEntryNumber,
--     secondaryEncoding           SEQUENCE SIZE(1..256) OF CapabilityTableEntryNumber OPTIONAL,
--     ...
-- }
-- 
-- -------------------------------------------------------------- --

--<ASN1.PDU
--		MULTIMEDIA-SYSTEM-CONTROL.RedundancyEncodingCapability>--
--<OSS.TYPENAME
--		MULTIMEDIA-SYSTEM-CONTROL.RedundancyEncodingCapability
--		"EmRedundancyEncodingCapability">--
--<OSS.FIELDNAME
--		MULTIMEDIA-SYSTEM-CONTROL.RedundancyEncodingCapability.redundancyEncodingMethod
--		"redundancyEncodingMethod">--
--<OSS.FIELDNAME
--		MULTIMEDIA-SYSTEM-CONTROL.RedundancyEncodingCapability.primaryEncoding
--		"primaryEncoding">--
--<OSS.FIELDNAME
--		MULTIMEDIA-SYSTEM-CONTROL.RedundancyEncodingCapability.secondaryEncoding
--		"secondaryEncoding">--
--<OSS.DefineName
--		MULTIMEDIA-SYSTEM-CONTROL.RedundancyEncodingCapability.secondaryEncoding
--		"EM_RedundancyEncodingCapability_secondaryEncoding">--

-- -------------------------------------------------------------- --
--
-- RedundancyEncodingMethod ::= CHOICE
-- {
--     nonStandard                     NonStandardParameter,
--     rtpAudioRedundancyEncoding      NULL,
--     ...,
--     rtpH263VideoRedundancyEncoding  RTPH263VideoRedundancyEncoding
-- }
-- 
-- -------------------------------------------------------------- --

--<ASN1.PDU
--		MULTIMEDIA-SYSTEM-CONTROL.RedundancyEncodingMethod>--
--<OSS.TYPENAME
--		MULTIMEDIA-SYSTEM-CONTROL.RedundancyEncodingMethod
--		"EmRedundancyEncodingMethod">--
--<OSS.FIELDNAME
--		MULTIMEDIA-SYSTEM-CONTROL.RedundancyEncodingMethod.nonStandard
--		"nonStandard">--
--<OSS.DefineName
--		MULTIMEDIA-SYSTEM-CONTROL.RedundancyEncodingMethod.nonStandard
--		"EM_RedundancyEncodingMethod_nonStandard">--
--<OSS.FIELDNAME
--		MULTIMEDIA-SYSTEM-CONTROL.RedundancyEncodingMethod.rtpAudioRedundancyEncoding
--		"rtpAudioRedundancyEncoding">--
--<OSS.DefineName
--		MULTIMEDIA-SYSTEM-CONTROL.RedundancyEncodingMethod.rtpAudioRedundancyEncoding
--		"EM_rtpAudioRedundancyEncoding">--
--<OSS.FIELDNAME
--		MULTIMEDIA-SYSTEM-CONTROL.RedundancyEncodingMethod.rtpH263VideoRedundancyEncoding
--		"rtpH263VideoRedundancyEncoding">--
--<OSS.DefineName
--		MULTIMEDIA-SYSTEM-CONTROL.RedundancyEncodingMethod.rtpH263VideoRedundancyEncoding
--		"EM_rtpH263VideoRedundancyEncoding">--

-- -------------------------------------------------------------- --
--
-- RTPH263VideoRedundancyEncoding ::= SEQUENCE
-- {
--     numberOfThreads         INTEGER(1..16),
--     framesBetweenSyncPoints INTEGER(1..256),
--     frameToThreadMapping    CHOICE
--     {
--             roundrobin      NULL,
--             custom          SEQUENCE SIZE(1..256) OF RTPH263VideoRedundancyFrameMapping,
--             ...
--     },
--     containedThreads        SEQUENCE SIZE(1..256) OF INTEGER (0..15) OPTIONAL,
--     ...
-- }
-- 
-- -------------------------------------------------------------- --

--<ASN1.PDU
--		MULTIMEDIA-SYSTEM-CONTROL.RTPH263VideoRedundancyEncoding>--
--<OSS.TYPENAME
--		MULTIMEDIA-SYSTEM-CONTROL.RTPH263VideoRedundancyEncoding
--		"EmRTPH263VideoRedundancyEncoding">--
--<OSS.FIELDNAME
--		MULTIMEDIA-SYSTEM-CONTROL.RTPH263VideoRedundancyEncoding.numberOfThreads
--		"numberOfThreads">--
--<OSS.FIELDNAME
--		MULTIMEDIA-SYSTEM-CONTROL.RTPH263VideoRedundancyEncoding.framesBetweenSyncPoints
--		"framesBetweenSyncPoints">--
--<OSS.FIELDNAME
--		MULTIMEDIA-SYSTEM-CONTROL.RTPH263VideoRedundancyEncoding.frameToThreadMapping
--		"frameToThreadMapping">--
--<OSS.ExtractType
--		MULTIMEDIA-SYSTEM-CONTROL.RTPH263VideoRedundancyEncoding.frameToThreadMapping>--
--<OSS.TYPENAME
--		MULTIMEDIA-SYSTEM-CONTROL.RTPH263VideoRedundancyEncoding.frameToThreadMapping
--		"EmFrameToThreadMapping">--
--<OSS.FIELDNAME
--		MULTIMEDIA-SYSTEM-CONTROL.RTPH263VideoRedundancyEncoding.frameToThreadMapping.roundrobin
--		"roundrobin">--
--<OSS.DefineName
--		MULTIMEDIA-SYSTEM-CONTROL.RTPH263VideoRedundancyEncoding.frameToThreadMapping.roundrobin
--		"EM_roundrobin">--
--<OSS.FIELDNAME
--		MULTIMEDIA-SYSTEM-CONTROL.RTPH263VideoRedundancyEncoding.frameToThreadMapping.custom
--		"custom">--
--<OSS.DefineName
--		MULTIMEDIA-SYSTEM-CONTROL.RTPH263VideoRedundancyEncoding.frameToThreadMapping.custom
--		"EM_custom">--
--<OSS.InlineType
--		MULTIMEDIA-SYSTEM-CONTROL.RTPH263VideoRedundancyEncoding.containedThreads>--
--<OSS.TYPENAME
--		MULTIMEDIA-SYSTEM-CONTROL.RTPH263VideoRedundancyEncoding.containedThreads
--		"EmContainedThreads">--
--<OSS.FIELDNAME
--		MULTIMEDIA-SYSTEM-CONTROL.RTPH263VideoRedundancyEncoding.containedThreads
--		"containedThreads">--
--<OSS.DefineName
--		MULTIMEDIA-SYSTEM-CONTROL.RTPH263VideoRedundancyEncoding.containedThreads
--		"EM_containedThreads">--

-- -------------------------------------------------------------- --
--
-- RTPH263VideoRedundancyFrameMapping ::= SEQUENCE
-- {
--     threadNumber    INTEGER (0..15),
--     frameSequence   SEQUENCE SIZE(1..256) OF INTEGER (0..255),
--     ...
-- }
-- 
-- -------------------------------------------------------------- --

--<ASN1.PDU
--		MULTIMEDIA-SYSTEM-CONTROL.RTPH263VideoRedundancyFrameMapping>--
--<OSS.TYPENAME
--		MULTIMEDIA-SYSTEM-CONTROL.RTPH263VideoRedundancyFrameMapping
--		"EmRTPH263VideoRedundancyFrameMapping">--
--<OSS.FIELDNAME
--		MULTIMEDIA-SYSTEM-CONTROL.RTPH263VideoRedundancyFrameMapping.threadNumber
--		"threadNumber">--
--<OSS.InlineType
--		MULTIMEDIA-SYSTEM-CONTROL.RTPH263VideoRedundancyFrameMapping.frameSequence>--
--<OSS.TYPENAME
--		MULTIMEDIA-SYSTEM-CONTROL.RTPH263VideoRedundancyFrameMapping.frameSequence
--		"EmFrameSequence">--
--<OSS.FIELDNAME
--		MULTIMEDIA-SYSTEM-CONTROL.RTPH263VideoRedundancyFrameMapping.frameSequence
--		"frameSequence">--

-- -------------------------------------------------------------- --
--
-- MultipointCapability ::= SEQUENCE
-- {
--     multicastCapability         BOOLEAN,
--     multiUniCastConference      BOOLEAN,
--     mediaDistributionCapability SEQUENCE OF MediaDistributionCapability,
--     ...
-- }
-- 
-- -------------------------------------------------------------- --

--<ASN1.PDU
--		MULTIMEDIA-SYSTEM-CONTROL.MultipointCapability>--
--<OSS.TYPENAME
--		MULTIMEDIA-SYSTEM-CONTROL.MultipointCapability
--		"EmMultipointCapability">--
--<OSS.FIELDNAME
--		MULTIMEDIA-SYSTEM-CONTROL.MultipointCapability.multicastCapability
--		"multicastCapability">--
--<OSS.FIELDNAME
--		MULTIMEDIA-SYSTEM-CONTROL.MultipointCapability.multiUniCastConference
--		"multiUniCastConference">--
--<OSS.FIELDNAME
--		MULTIMEDIA-SYSTEM-CONTROL.MultipointCapability.mediaDistributionCapability
--		"mediaDistributionCapability">--

-- -------------------------------------------------------------- --
-- 
-- MediaDistributionCapability ::= SEQUENCE
-- {
--     centralizedControl  BOOLEAN,
--     distributedControl  BOOLEAN,
--     centralizedAudio    BOOLEAN,
--     distributedAudio    BOOLEAN,
--     centralizedVideo    BOOLEAN,
--     distributedVideo    BOOLEAN,
--     centralizedData SEQUENCE OF DataApplicationCapability OPTIONAL,
--     distributedData SEQUENCE OF DataApplicationCapability OPTIONAL,
--     ...
-- }
-- 
-- -------------------------------------------------------------- --

--<ASN1.PDU
--		MULTIMEDIA-SYSTEM-CONTROL.MediaDistributionCapability>--
--<OSS.TYPENAME
--		MULTIMEDIA-SYSTEM-CONTROL.MediaDistributionCapability
--		"EmMediaDistributionCapability">--
--<OSS.FIELDNAME
--		MULTIMEDIA-SYSTEM-CONTROL.MediaDistributionCapability.centralizedControl
--		"centralizedControl">--
--<OSS.FIELDNAME
--		MULTIMEDIA-SYSTEM-CONTROL.MediaDistributionCapability.distributedControl
--		"distributedControl">--
--<OSS.FIELDNAME
--		MULTIMEDIA-SYSTEM-CONTROL.MediaDistributionCapability.centralizedAudio
--		"centralizedAudio">--
--<OSS.FIELDNAME
--		MULTIMEDIA-SYSTEM-CONTROL.MediaDistributionCapability.distributedAudio
--		"distributedAudio">--
--<OSS.FIELDNAME
--		MULTIMEDIA-SYSTEM-CONTROL.MediaDistributionCapability.centralizedVideo
--		"centralizedVideo">--
--<OSS.FIELDNAME
--		MULTIMEDIA-SYSTEM-CONTROL.MediaDistributionCapability.distributedVideo
--		"distributedVideo">--
--<OSS.FIELDNAME
--		MULTIMEDIA-SYSTEM-CONTROL.MediaDistributionCapability.centralizedData
--		"centralizedData">--
--<OSS.DefineName
--		MULTIMEDIA-SYSTEM-CONTROL.MediaDistributionCapability.centralizedData
--		"EM_centralizedData">--
--<OSS.FIELDNAME
--		MULTIMEDIA-SYSTEM-CONTROL.MediaDistributionCapability.distributedData
--		"distributedData">--
--<OSS.DefineName
--		MULTIMEDIA-SYSTEM-CONTROL.MediaDistributionCapability.distributedData
--		"EM_distributedData">--

-- ==============================================================
-- Capability exchange definitions: Video capabilities
-- ==============================================================

-- -------------------------------------------------------------- --
-- 
-- VideoCapability ::= CHOICE
-- {
--     nonStandard             NonStandardParameter,
--     h261VideoCapability     H261VideoCapability,
--     h262VideoCapability     H262VideoCapability,
--     h263VideoCapability     H263VideoCapability,
--     is11172VideoCapability  IS11172VideoCapability,
--     ...
-- }
-- 
-- -------------------------------------------------------------- --

--<ASN1.PDU
--		MULTIMEDIA-SYSTEM-CONTROL.VideoCapability>--
--<OSS.TYPENAME
--		MULTIMEDIA-SYSTEM-CONTROL.VideoCapability
--		"EmVideoCapability">--
--<OSS.FIELDNAME
--		MULTIMEDIA-SYSTEM-CONTROL.VideoCapability.nonStandard
--		"nonStandard">--
--<OSS.DefineName
--		MULTIMEDIA-SYSTEM-CONTROL.VideoCapability.nonStandard
--		"EM_VideoCapability_nonStandard">--
--<OSS.FIELDNAME
--		MULTIMEDIA-SYSTEM-CONTROL.VideoCapability.h261VideoCapability
--		"h261VideoCapability">--
--<OSS.DefineName
--		MULTIMEDIA-SYSTEM-CONTROL.VideoCapability.h261VideoCapability
--		"EM_h261VideoCapability">--
--<OSS.FIELDNAME
--		MULTIMEDIA-SYSTEM-CONTROL.VideoCapability.h262VideoCapability
--		"h262VideoCapability">--
--<OSS.DefineName
--		MULTIMEDIA-SYSTEM-CONTROL.VideoCapability.h262VideoCapability
--		"EM_h262VideoCapability">--
--<OSS.FIELDNAME
--		MULTIMEDIA-SYSTEM-CONTROL.VideoCapability.h263VideoCapability
--		"h263VideoCapability">--
--<OSS.DefineName
--		MULTIMEDIA-SYSTEM-CONTROL.VideoCapability.h263VideoCapability
--		"EM_h263VideoCapability">--
--<OSS.FIELDNAME
--		MULTIMEDIA-SYSTEM-CONTROL.VideoCapability.is11172VideoCapability
--		"is11172VideoCapability">--
--<OSS.DefineName
--		MULTIMEDIA-SYSTEM-CONTROL.VideoCapability.is11172VideoCapability
--		"EM_is11172VideoCapability">--

-- -------------------------------------------------------------- --
--  
-- H261VideoCapability ::= SEQUENCE
-- {
--     qcifMPI                             INTEGER (1..4)  OPTIONAL,
--     cifMPI                              INTEGER (1..4)  OPTIONAL,
--     temporalSpatialTradeOffCapability   BOOLEAN,
--     maxBitRate                          INTEGER (1..19200),
--     stillImageTransmission              BOOLEAN,
--     ...
-- }
-- 
-- -------------------------------------------------------------- --

--<ASN1.PDU
--		MULTIMEDIA-SYSTEM-CONTROL.H261VideoCapability>--
--<OSS.TYPENAME
--		MULTIMEDIA-SYSTEM-CONTROL.H261VideoCapability
--		"EmH261VideoCapability">--
--<OSS.FIELDNAME
--		MULTIMEDIA-SYSTEM-CONTROL.H261VideoCapability.qcifMPI
--		"qcifMPI">--
--<OSS.DefineName
--		MULTIMEDIA-SYSTEM-CONTROL.H261VideoCapability.qcifMPI
--		"EM_H261VideoCapability_qcifMPI">--
--<OSS.FIELDNAME
--		MULTIMEDIA-SYSTEM-CONTROL.H261VideoCapability.cifMPI
--		"cifMPI">--
--<OSS.DefineName
--		MULTIMEDIA-SYSTEM-CONTROL.H261VideoCapability.cifMPI
--		"EM_H261VideoCapability_cifMPI">--
--<OSS.FIELDNAME
--		MULTIMEDIA-SYSTEM-CONTROL.H261VideoCapability.temporalSpatialTradeOffCapability
--		"temporalSpatialTradeOffCapability">--
--<OSS.FIELDNAME
--		MULTIMEDIA-SYSTEM-CONTROL.H261VideoCapability.maxBitRate
--		"maxBitRate">--
--<OSS.FIELDNAME
--		MULTIMEDIA-SYSTEM-CONTROL.H261VideoCapability.stillImageTransmission
--		"stillImageTransmission">--

-- -------------------------------------------------------------- --
--  
-- H262VideoCapability ::= SEQUENCE
-- {
--     profileAndLevel-SPatML          BOOLEAN,
--     profileAndLevel-MPatLL          BOOLEAN,
--     profileAndLevel-MPatML          BOOLEAN,
--     profileAndLevel-MPatH-14        BOOLEAN,
--     profileAndLevel-MPatHL          BOOLEAN,
--     profileAndLevel-SNRatLL         BOOLEAN,
--     profileAndLevel-SNRatML         BOOLEAN,
--     profileAndLevel-SpatialatH-14   BOOLEAN,
--     profileAndLevel-HPatML          BOOLEAN,
--     profileAndLevel-HPatH-14        BOOLEAN,
--     profileAndLevel-HPatHL          BOOLEAN,
--  
--     videoBitRate        INTEGER(0.. 1073741823) OPTIONAL,
--     vbvBufferSize       INTEGER(0.. 262143) OPTIONAL,
--     samplesPerLine      INTEGER(0..16383) OPTIONAL,
--     linesPerFrame       INTEGER(0..16383) OPTIONAL,
--     framesPerSecond     INTEGER(0..15) OPTIONAL,
--     luminanceSampleRate INTEGER(0..4294967295) OPTIONAL,
--     ...
-- }
-- 
-- -------------------------------------------------------------- --

--<ASN1.PDU
--		MULTIMEDIA-SYSTEM-CONTROL.H262VideoCapability>--
--<OSS.TYPENAME
--		MULTIMEDIA-SYSTEM-CONTROL.H262VideoCapability
--		"EmH262VideoCapability">--
--<OSS.FIELDNAME
--		MULTIMEDIA-SYSTEM-CONTROL.H262VideoCapability.profileAndLevel-SPatML
--		"profileAndLevel_SPatML">--
--<OSS.FIELDNAME
--		MULTIMEDIA-SYSTEM-CONTROL.H262VideoCapability.profileAndLevel-MPatLL
--		"profileAndLevel_MPatLL">--
--<OSS.FIELDNAME
--		MULTIMEDIA-SYSTEM-CONTROL.H262VideoCapability.profileAndLevel-MPatML
--		"profileAndLevel_MPatML">--
--<OSS.FIELDNAME
--		MULTIMEDIA-SYSTEM-CONTROL.H262VideoCapability.profileAndLevel-MPatH-14
--		"profileAndLevel_MPatH_14">--
--<OSS.FIELDNAME
--		MULTIMEDIA-SYSTEM-CONTROL.H262VideoCapability.profileAndLevel-MPatHL
--		"profileAndLevel_MPatHL">--
--<OSS.FIELDNAME
--		MULTIMEDIA-SYSTEM-CONTROL.H262VideoCapability.profileAndLevel-SNRatLL
--		"profileAndLevel_SNRatLL">--
--<OSS.FIELDNAME
--		MULTIMEDIA-SYSTEM-CONTROL.H262VideoCapability.profileAndLevel-SNRatML
--		"profileAndLevel_SNRatML">--
--<OSS.FIELDNAME
--		MULTIMEDIA-SYSTEM-CONTROL.H262VideoCapability.profileAndLevel-SpatialatH-14
--		"profileAndLevel_SpatialatH_14">--
--<OSS.FIELDNAME
--		MULTIMEDIA-SYSTEM-CONTROL.H262VideoCapability.profileAndLevel-HPatML
--		"profileAndLevel_HPatML">--
--<OSS.FIELDNAME
--		MULTIMEDIA-SYSTEM-CONTROL.H262VideoCapability.profileAndLevel-HPatH-14
--		"profileAndLevel_HPatH_14">--
--<OSS.FIELDNAME
--		MULTIMEDIA-SYSTEM-CONTROL.H262VideoCapability.profileAndLevel-HPatHL
--		"profileAndLevel_HPatHL">--
--<OSS.FIELDNAME
--		MULTIMEDIA-SYSTEM-CONTROL.H262VideoCapability.videoBitRate
--		"videoBitRate">--
--<OSS.DefineName
--		MULTIMEDIA-SYSTEM-CONTROL.H262VideoCapability.videoBitRate
--		"EM_H262VideoCapability_videoBitRate">--
--<OSS.FIELDNAME
--		MULTIMEDIA-SYSTEM-CONTROL.H262VideoCapability.vbvBufferSize
--		"vbvBufferSize">--
--<OSS.DefineName
--		MULTIMEDIA-SYSTEM-CONTROL.H262VideoCapability.vbvBufferSize
--		"EM_H262VideoCapability_vbvBufferSize">--
--<OSS.FIELDNAME
--		MULTIMEDIA-SYSTEM-CONTROL.H262VideoCapability.samplesPerLine
--		"samplesPerLine">--
--<OSS.DefineName
--		MULTIMEDIA-SYSTEM-CONTROL.H262VideoCapability.samplesPerLine
--		"EM_H262VideoCapability_samplesPerLine">--
--<OSS.FIELDNAME
--		MULTIMEDIA-SYSTEM-CONTROL.H262VideoCapability.linesPerFrame
--		"linesPerFrame">--
--<OSS.DefineName
--		MULTIMEDIA-SYSTEM-CONTROL.H262VideoCapability.linesPerFrame
--		"EM_H262VideoCapability_linesPerFrame">--
--<OSS.FIELDNAME
--		MULTIMEDIA-SYSTEM-CONTROL.H262VideoCapability.framesPerSecond
--		"framesPerSecond">--
--<OSS.DefineName
--		MULTIMEDIA-SYSTEM-CONTROL.H262VideoCapability.framesPerSecond
--		"EM_H262VideoCapability_framesPerSecond">--
--<OSS.FIELDNAME
--		MULTIMEDIA-SYSTEM-CONTROL.H262VideoCapability.luminanceSampleRate
--		"luminanceSampleRate">--
--<OSS.DefineName
--		MULTIMEDIA-SYSTEM-CONTROL.H262VideoCapability.luminanceSampleRate
--		"EM_H262VideoCapability_luminanceSampleRate">--

-- -------------------------------------------------------------- --
--  
-- H263VideoCapability ::= SEQUENCE
-- {
--     sqcifMPI    INTEGER (1..32)  OPTIONAL,
--     qcifMPI     INTEGER (1..32)  OPTIONAL,
--     cifMPI      INTEGER (1..32)  OPTIONAL,
--     cif4MPI     INTEGER (1..32)  OPTIONAL,
--     cif16MPI    INTEGER (1..32)  OPTIONAL,
--     maxBitRate  INTEGER (1..192400),
--     unrestrictedVector  BOOLEAN,
--     arithmeticCoding    BOOLEAN,
--     advancedPrediction  BOOLEAN,
--     pbFrames            BOOLEAN,
--     temporalSpatialTradeOffCapability   BOOLEAN,
--     hrd-B       INTEGER (0..524287)  OPTIONAL,
--     bppMaxKb    INTEGER (0..65535)  OPTIONAL,
--     ...,
--  
--     slowSqcifMPI        INTEGER (1..3600)  OPTIONAL,
--     slowQcifMPI         INTEGER (1..3600)  OPTIONAL,
--     slowCifMPI          INTEGER (1..3600)  OPTIONAL,
--     slowCif4MPI         INTEGER (1..3600)  OPTIONAL,
--     slowCif16MPI        INTEGER (1..3600)  OPTIONAL,
--     errorCompensation   BOOLEAN
--  
--     enhancementLayerInfo    EnhancementLayerInfo OPTIONAL,
--     h263Options             H263Options OPTIONAL
-- }
-- 
-- -------------------------------------------------------------- --

--<ASN1.PDU
--		MULTIMEDIA-SYSTEM-CONTROL.H263VideoCapability>--
--<OSS.TYPENAME
--		MULTIMEDIA-SYSTEM-CONTROL.H263VideoCapability
--		"EmH263VideoCapability">--
--<OSS.FIELDNAME
--		MULTIMEDIA-SYSTEM-CONTROL.H263VideoCapability.sqcifMPI
--		"sqcifMPI">--
--<OSS.DefineName
--		MULTIMEDIA-SYSTEM-CONTROL.H263VideoCapability.sqcifMPI
--		"EM_H263VideoCapability_sqcifMPI">--
--<OSS.FIELDNAME
--		MULTIMEDIA-SYSTEM-CONTROL.H263VideoCapability.qcifMPI
--		"qcifMPI">--
--<OSS.DefineName
--		MULTIMEDIA-SYSTEM-CONTROL.H263VideoCapability.qcifMPI
--		"EM_H263VideoCapability_qcifMPI">--
--<OSS.FIELDNAME
--		MULTIMEDIA-SYSTEM-CONTROL.H263VideoCapability.cifMPI
--		"cifMPI">--
--<OSS.DefineName
--		MULTIMEDIA-SYSTEM-CONTROL.H263VideoCapability.cifMPI
--		"EM_H263VideoCapability_cifMPI">--
--<OSS.FIELDNAME
--		MULTIMEDIA-SYSTEM-CONTROL.H263VideoCapability.cif4MPI
--		"cif4MPI">--
--<OSS.DefineName
--		MULTIMEDIA-SYSTEM-CONTROL.H263VideoCapability.cif4MPI
--		"EM_H263VideoCapability_cif4MPI">--
--<OSS.FIELDNAME
--		MULTIMEDIA-SYSTEM-CONTROL.H263VideoCapability.cif16MPI
--		"cif16MPI">--
--<OSS.DefineName
--		MULTIMEDIA-SYSTEM-CONTROL.H263VideoCapability.cif16MPI
--		"EM_H263VideoCapability_cif16MPI">--
--<OSS.FIELDNAME
--		MULTIMEDIA-SYSTEM-CONTROL.H263VideoCapability.maxBitRate
--		"maxBitRate">--
--<OSS.FIELDNAME
--		MULTIMEDIA-SYSTEM-CONTROL.H263VideoCapability.unrestrictedVector
--		"unrestrictedVector">--
--<OSS.FIELDNAME
--		MULTIMEDIA-SYSTEM-CONTROL.H263VideoCapability.arithmeticCoding
--		"arithmeticCoding">--
--<OSS.FIELDNAME
--		MULTIMEDIA-SYSTEM-CONTROL.H263VideoCapability.advancedPrediction
--		"advancedPrediction">--
--<OSS.FIELDNAME
--		MULTIMEDIA-SYSTEM-CONTROL.H263VideoCapability.pbFrames
--		"pbFrames">--
--<OSS.FIELDNAME
--		MULTIMEDIA-SYSTEM-CONTROL.H263VideoCapability.temporalSpatialTradeOffCapability
--		"temporalSpatialTradeOffCapability">--
--<OSS.FIELDNAME
--		MULTIMEDIA-SYSTEM-CONTROL.H263VideoCapability.hrd-B
--		"hrd_B">--
--<OSS.DefineName
--		MULTIMEDIA-SYSTEM-CONTROL.H263VideoCapability.hrd-B
--		"EM_hrd_B">--
--<OSS.FIELDNAME
--		MULTIMEDIA-SYSTEM-CONTROL.H263VideoCapability.bppMaxKb
--		"bppMaxKb">--
--<OSS.DefineName
--		MULTIMEDIA-SYSTEM-CONTROL.H263VideoCapability.bppMaxKb
--		"EM_bppMaxKb">--
--<OSS.FIELDNAME
--		MULTIMEDIA-SYSTEM-CONTROL.H263VideoCapability.slowSqcifMPI
--		"slowSqcifMPI">--
--<OSS.DefineName
--		MULTIMEDIA-SYSTEM-CONTROL.H263VideoCapability.slowSqcifMPI
--		"EM_H263VideoCapability_slowSqcifMPI">--
--<OSS.FIELDNAME
--		MULTIMEDIA-SYSTEM-CONTROL.H263VideoCapability.slowQcifMPI
--		"slowQcifMPI">--
--<OSS.DefineName
--		MULTIMEDIA-SYSTEM-CONTROL.H263VideoCapability.slowQcifMPI
--		"EM_H263VideoCapability_slowQcifMPI">--
--<OSS.FIELDNAME
--		MULTIMEDIA-SYSTEM-CONTROL.H263VideoCapability.slowCifMPI
--		"slowCifMPI">--
--<OSS.DefineName
--		MULTIMEDIA-SYSTEM-CONTROL.H263VideoCapability.slowCifMPI
--		"EM_H263VideoCapability_slowCifMPI">--
--<OSS.FIELDNAME
--		MULTIMEDIA-SYSTEM-CONTROL.H263VideoCapability.slowCif4MPI
--		"slowCif4MPI">--
--<OSS.DefineName
--		MULTIMEDIA-SYSTEM-CONTROL.H263VideoCapability.slowCif4MPI
--		"EM_H263VideoCapability_slowCif4MPI">--
--<OSS.FIELDNAME
--		MULTIMEDIA-SYSTEM-CONTROL.H263VideoCapability.slowCif16MPI
--		"slowCif16MPI">--
--<OSS.DefineName
--		MULTIMEDIA-SYSTEM-CONTROL.H263VideoCapability.slowCif16MPI
--		"EM_H263VideoCapability_slowCif16MPI">--
--<OSS.FIELDNAME
--		MULTIMEDIA-SYSTEM-CONTROL.H263VideoCapability.errorCompensation
--		"errorCompensation">--
--<OSS.DefineName
--		MULTIMEDIA-SYSTEM-CONTROL.H263VideoCapability.errorCompensation
--		"EM_H263VideoCapability_errorCompensation">--
--<OSS.FIELDNAME
--		MULTIMEDIA-SYSTEM-CONTROL.H263VideoCapability.enhancementLayerInfo
--		"enhancementLayerInfo">--
--<OSS.DefineName
--		MULTIMEDIA-SYSTEM-CONTROL.H263VideoCapability.enhancementLayerInfo
--		"EM_H263VideoCapability_enhancementLayerInfo">--
--<OSS.FIELDNAME
--		MULTIMEDIA-SYSTEM-CONTROL.H263VideoCapability.h263Options
--		"h263Options">--
--<OSS.DefineName
--		MULTIMEDIA-SYSTEM-CONTROL.H263VideoCapability.h263Options
--		"EM_H263VideoCapability_h263Options">--

-- -------------------------------------------------------------- --
--
-- EnhancementLayerInfo ::= SEQUENCE
-- {
--     baseBitRateConstrained  BOOLEAN,
--     snrEnhancement          SET SIZE(1..14) OF EnhancementOptions OPTIONAL,
--     spatialEnhancement      SET SIZE(1..14) OF EnhancementOptions OPTIONAL,
--     bPictureEnhancement     SET SIZE(1..14) OF BEnhancementParameters OPTIONAL,
--     ...
-- }
--
-- -------------------------------------------------------------- --

--<ASN1.PDU
--		MULTIMEDIA-SYSTEM-CONTROL.EnhancementLayerInfo>--
--<OSS.TYPENAME
--		MULTIMEDIA-SYSTEM-CONTROL.EnhancementLayerInfo
--		"EmEnhancementLayerInfo">--
--<OSS.FIELDNAME
--		MULTIMEDIA-SYSTEM-CONTROL.EnhancementLayerInfo.baseBitRateConstrained
--		"baseBitRateConstrained">--
--<OSS.FIELDNAME
--		MULTIMEDIA-SYSTEM-CONTROL.EnhancementLayerInfo.snrEnhancement
--		"snrEnhancement">--
--<OSS.DefineName
--		MULTIMEDIA-SYSTEM-CONTROL.EnhancementLayerInfo.snrEnhancement
--		"EM_snrEnhancement">--
--<OSS.FIELDNAME
--		MULTIMEDIA-SYSTEM-CONTROL.EnhancementLayerInfo.spatialEnhancement
--		"spatialEnhancement">--
--<OSS.DefineName
--		MULTIMEDIA-SYSTEM-CONTROL.EnhancementLayerInfo.spatialEnhancement
--		"EM_spatialEnhancement">--
--<OSS.FIELDNAME
--		MULTIMEDIA-SYSTEM-CONTROL.EnhancementLayerInfo.bPictureEnhancement
--		"bPictureEnhancement">--
--<OSS.DefineName
--		MULTIMEDIA-SYSTEM-CONTROL.EnhancementLayerInfo.bPictureEnhancement
--		"EM_bPictureEnhancement">--

-- -------------------------------------------------------------- --
--
-- BEnhancementParameters ::= SEQUENCE
-- {
--     enhancementOptions  EnhancementOptions,
--     numberOfBPictures   INTEGER(1..64),
--     ...
-- }
--
-- -------------------------------------------------------------- --

--<ASN1.PDU
--		MULTIMEDIA-SYSTEM-CONTROL.BEnhancementParameters>--
--<OSS.TYPENAME
--		MULTIMEDIA-SYSTEM-CONTROL.BEnhancementParameters
--		"EmBEnhancementParameters">--
--<OSS.FIELDNAME
--		MULTIMEDIA-SYSTEM-CONTROL.BEnhancementParameters.enhancementOptions
--		"enhancementOptions">--
--<OSS.FIELDNAME
--		MULTIMEDIA-SYSTEM-CONTROL.BEnhancementParameters.numberOfBPictures
--		"numberOfBPictures">--

-- -------------------------------------------------------------- --
--
-- EnhancementOptions  ::=SEQUENCE
-- {
--     sqcifMPI            INTEGER(1..32) OPTIONAL,
--     qcifMPI             INTEGER(1..32) OPTIONAL,
--     cifMPI              INTEGER(1..32) OPTIONAL,
--     cif4MPI             INTEGER(1..32) OPTIONAL,
--     cif16MPI            INTEGER(1..32) OPTIONAL,
--     maxBitRate          INTEGER(1..192400),
--     unrestrictedVector  BOOLEAN,
--     arithmeticCoding    BOOLEAN,
--     temporalSpatialTradeOffCapability   BOOLEAN,
--     slowSqcifMPI        INTEGER (1..3600) OPTIONAL,
--     slowQcifMPI         INTEGER (1..3600) OPTIONAL,
--     slowCifMPI          INTEGER (1..3600) OPTIONAL,
--     slowCif4MPI         INTEGER (1..3600) OPTIONAL,
--     slowCif16MPI        INTEGER (1..3600) OPTIONAL,
--     errorCompensation   BOOLEAN,
--     h263Options         H263Options OPTIONAL,
--     ...
-- }
--
-- -------------------------------------------------------------- --

--<ASN1.PDU
--		MULTIMEDIA-SYSTEM-CONTROL.EnhancementOptions>--
--<OSS.TYPENAME
--		MULTIMEDIA-SYSTEM-CONTROL.EnhancementOptions
--		"EmEnhancementOptions">--
--<OSS.FIELDNAME
--		MULTIMEDIA-SYSTEM-CONTROL.EnhancementOptions.sqcifMPI
--		"sqcifMPI">--
--<OSS.DefineName
--		MULTIMEDIA-SYSTEM-CONTROL.EnhancementOptions.sqcifMPI
--		"EM_EnhancementOptions_sqcifMPI">--
--<OSS.FIELDNAME
--		MULTIMEDIA-SYSTEM-CONTROL.EnhancementOptions.qcifMPI
--		"qcifMPI">--
--<OSS.DefineName
--		MULTIMEDIA-SYSTEM-CONTROL.EnhancementOptions.qcifMPI
--		"EM_EnhancementOptions_qcifMPI">--
--<OSS.FIELDNAME
--      MULTIMEDIA-SYSTEM-CONTROL.EnhancementOptions.cifMPI
--      "cifMPI">--
--<OSS.DefineName
--      MULTIMEDIA-SYSTEM-CONTROL.EnhancementOptions.cifMPI
--      "EM_EnhancementOptions_cifMPI">--
--<OSS.FIELDNAME
--      MULTIMEDIA-SYSTEM-CONTROL.EnhancementOptions.cif4MPI
--      "cif4MPI">--
--<OSS.DefineName
--      MULTIMEDIA-SYSTEM-CONTROL.EnhancementOptions.cif4MPI
--      "EM_EnhancementOptions_cif4MPI">--
--<OSS.FIELDNAME
--      MULTIMEDIA-SYSTEM-CONTROL.EnhancementOptions.cif16MPI
--      "cif16MPI">--
--<OSS.DefineName
--      MULTIMEDIA-SYSTEM-CONTROL.EnhancementOptions.cif16MPI
--      "EM_EnhancementOptions_cif16MPI">--
--<OSS.FIELDNAME
--      MULTIMEDIA-SYSTEM-CONTROL.EnhancementOptions.maxBitRate
--      "maxBitRate">--
--<OSS.FIELDNAME
--      MULTIMEDIA-SYSTEM-CONTROL.EnhancementOptions.unrestrictedVector
--      "unrestrictedVector">--
--<OSS.FIELDNAME
--      MULTIMEDIA-SYSTEM-CONTROL.EnhancementOptions.arithmeticCoding
--      "arithmeticCoding">--
--<OSS.FIELDNAME
--      MULTIMEDIA-SYSTEM-CONTROL.EnhancementOptions.temporalSpatialTradeOffCapability
--      "temporalSpatialTradeOffCapability">--
--<OSS.FIELDNAME
--      MULTIMEDIA-SYSTEM-CONTROL.EnhancementOptions.slowSqcifMPI
--      "slowSqcifMPI">--
--<OSS.DefineName
--      MULTIMEDIA-SYSTEM-CONTROL.EnhancementOptions.slowSqcifMPI
--      "EM_EnhancementOptions_slowSqcifMPI">--
--<OSS.FIELDNAME
--      MULTIMEDIA-SYSTEM-CONTROL.EnhancementOptions.slowQcifMPI
--      "slowQcifMPI">--
--<OSS.DefineName
--      MULTIMEDIA-SYSTEM-CONTROL.EnhancementOptions.slowQcifMPI
--      "EM_EnhancementOptions_slowQcifMPI">--
--<OSS.FIELDNAME
--      MULTIMEDIA-SYSTEM-CONTROL.EnhancementOptions.slowCifMPI
--      "slowCifMPI">--
--<OSS.DefineName
--      MULTIMEDIA-SYSTEM-CONTROL.EnhancementOptions.slowCifMPI
--      "EM_EnhancementOptions_slowCifMPI">--
--<OSS.FIELDNAME
--      MULTIMEDIA-SYSTEM-CONTROL.EnhancementOptions.slowCif4MPI
--      "slowCif4MPI">--
--<OSS.DefineName
--      MULTIMEDIA-SYSTEM-CONTROL.EnhancementOptions.slowCif4MPI
--      "EM_EnhancementOptions_slowCif4MPI">--
--<OSS.FIELDNAME
--      MULTIMEDIA-SYSTEM-CONTROL.EnhancementOptions.slowCif16MPI
--      "slowCif16MPI">--
--<OSS.DefineName
--      MULTIMEDIA-SYSTEM-CONTROL.EnhancementOptions.slowCif16MPI
--      "EM_EnhancementOptions_slowCif16MPI">--
--<OSS.FIELDNAME
--      MULTIMEDIA-SYSTEM-CONTROL.EnhancementOptions.errorCompensation
--      "errorCompensation">--
--<OSS.FIELDNAME
--      MULTIMEDIA-SYSTEM-CONTROL.EnhancementOptions.h263Options
--      "h263Options">--
--<OSS.DefineName
--      MULTIMEDIA-SYSTEM-CONTROL.EnhancementOptions.h263Options
--      "EM_EnhancementOptions_h263Options">--

-- -------------------------------------------------------------- --
--
-- H263Options ::= SEQUENCE
-- {
--     advancedIntraCodingMode         BOOLEAN,
--     deblockingFilterMode            BOOLEAN,
--     improvedPBFramesMode            BOOLEAN,
--  
--     unlimitedMotionVectors          BOOLEAN,
--  
--     fullPictureFreeze               BOOLEAN,
--     partialPictureFreezeAndRelease  BOOLEAN,
--     resizingPartPicFreezeAndRelease BOOLEAN,
--     fullPictureSnapshot             BOOLEAN,
--     partialPictureSnapshot          BOOLEAN,
--     videoSegmentTagging             BOOLEAN,
--     progressiveRefinement           BOOLEAN,
--  
--     dynamicPictureResizingByFour        BOOLEAN,
--     dynamicPictureResizingSixteenthPel  BOOLEAN,
--     dynamicWarpingHalfPel               BOOLEAN,
--     dynamicWarpingSixteenthPel          BOOLEAN,
--  
--     independentSegmentDecoding      BOOLEAN,
--  
--     slicesInOrder-NonRect           BOOLEAN,
--     slicesInOrder-Rect              BOOLEAN,
--     slicesNoOrder-NonRect           BOOLEAN,
--     slicesNoOrder-Rect              BOOLEAN,
--  
--     alternateInterVLCMode           BOOLEAN,
--     modifiedQuantizationMode        BOOLEAN,
--     reducedResolutionUpdate         BOOLEAN,
--  
--     transparencyParameters          TransparencyParameters OPTIONAL,
--     separateVideoBackChannel        BOOLEAN,
--     refPictureSelection             RefPictureSelection OPTIONAL,
--     customPictureClockFrequency     SET SIZE (1..16) OF CustomPictureClockFrequency  OPTIONAL,
--     customPictureFormat             SET SIZE (1..16) OF CustomPictureFormat OPTIONAL,
--     modeCombos                      SET SIZE (1..16) OF H263VideoModeCombos OPTIONAL,
--     ...
-- }
--
-- -------------------------------------------------------------- --

--<ASN1.PDU
--		MULTIMEDIA-SYSTEM-CONTROL.H263Options>--
--<OSS.TYPENAME
--		MULTIMEDIA-SYSTEM-CONTROL.H263Options
--		"EmH263Options">--
--<OSS.FIELDNAME
--      MULTIMEDIA-SYSTEM-CONTROL.H263Options.advancedIntraCodingMode
--      "advancedIntraCodingMode">--
--<OSS.FIELDNAME
--      MULTIMEDIA-SYSTEM-CONTROL.H263Options.deblockingFilterMode
--      "deblockingFilterMode">--
--<OSS.FIELDNAME
--      MULTIMEDIA-SYSTEM-CONTROL.H263Options.improvedPBFramesMode
--      "improvedPBFramesMode">--
--<OSS.FIELDNAME
--      MULTIMEDIA-SYSTEM-CONTROL.H263Options.unlimitedMotionVectors
--      "unlimitedMotionVectors">--
--<OSS.FIELDNAME
--      MULTIMEDIA-SYSTEM-CONTROL.H263Options.fullPictureFreeze
--      "fullPictureFreeze">--
--<OSS.FIELDNAME
--      MULTIMEDIA-SYSTEM-CONTROL.H263Options.partialPictureFreezeAndRelease
--      "partialPictureFreezeAndRelease">--
--<OSS.FIELDNAME
--      MULTIMEDIA-SYSTEM-CONTROL.H263Options.resizingPartPicFreezeAndRelease
--      "resizingPartPicFreezeAndRelease">--
--<OSS.FIELDNAME
--      MULTIMEDIA-SYSTEM-CONTROL.H263Options.fullPictureSnapshot
--      "fullPictureSnapshot">--
--<OSS.FIELDNAME
--      MULTIMEDIA-SYSTEM-CONTROL.H263Options.partialPictureSnapshot
--      "partialPictureSnapshot">--
--<OSS.FIELDNAME
--      MULTIMEDIA-SYSTEM-CONTROL.H263Options.videoSegmentTagging
--      "videoSegmentTagging">--
--<OSS.FIELDNAME
--      MULTIMEDIA-SYSTEM-CONTROL.H263Options.progressiveRefinement
--      "progressiveRefinement">--
--<OSS.FIELDNAME
--      MULTIMEDIA-SYSTEM-CONTROL.H263Options.dynamicPictureResizingByFour
--      "dynamicPictureResizingByFour">--
--<OSS.FIELDNAME
--      MULTIMEDIA-SYSTEM-CONTROL.H263Options.dynamicPictureResizingSixteenthPel
--      "dynamicPictureResizingSixteenthPel">--
--<OSS.FIELDNAME
--      MULTIMEDIA-SYSTEM-CONTROL.H263Options.dynamicWarpingHalfPel
--      "dynamicWarpingHalfPel">--
--<OSS.FIELDNAME
--      MULTIMEDIA-SYSTEM-CONTROL.H263Options.dynamicWarpingSixteenthPel
--      "dynamicWarpingSixteenthPel">--
--<OSS.FIELDNAME
--      MULTIMEDIA-SYSTEM-CONTROL.H263Options.independentSegmentDecoding
--      "independentSegmentDecoding">--
--<OSS.FIELDNAME
--      MULTIMEDIA-SYSTEM-CONTROL.H263Options.slicesInOrder-NonRect
--      "slicesInOrder_NonRect">--
--<OSS.FIELDNAME
--      MULTIMEDIA-SYSTEM-CONTROL.H263Options.slicesInOrder-Rect
--      "slicesInOrder_Rect">--
--<OSS.FIELDNAME
--      MULTIMEDIA-SYSTEM-CONTROL.H263Options.slicesNoOrder-NonRect
--      "slicesNoOrder_NonRect">--
--<OSS.FIELDNAME
--      MULTIMEDIA-SYSTEM-CONTROL.H263Options.slicesNoOrder-Rect
--      "slicesNoOrder_Rect">--
--<OSS.FIELDNAME
--      MULTIMEDIA-SYSTEM-CONTROL.H263Options.alternateInterVLCMode
--      "alternateInterVLCMode">--
--<OSS.FIELDNAME
--      MULTIMEDIA-SYSTEM-CONTROL.H263Options.modifiedQuantizationMode
--      "modifiedQuantizationMode">--
--<OSS.FIELDNAME
--      MULTIMEDIA-SYSTEM-CONTROL.H263Options.reducedResolutionUpdate
--      "reducedResolutionUpdate">--
--<OSS.FIELDNAME
--      MULTIMEDIA-SYSTEM-CONTROL.H263Options.transparencyParameters
--      "transparencyParameters">--
--<OSS.DefineName
--      MULTIMEDIA-SYSTEM-CONTROL.H263Options.transparencyParameters
--      "EM_transparencyParameters">--
--<OSS.FIELDNAME
--      MULTIMEDIA-SYSTEM-CONTROL.H263Options.separateVideoBackChannel
--      "separateVideoBackChannel">--
--<OSS.FIELDNAME
--      MULTIMEDIA-SYSTEM-CONTROL.H263Options.refPictureSelection
--      "refPictureSelection">--
--<OSS.DefineName
--      MULTIMEDIA-SYSTEM-CONTROL.H263Options.refPictureSelection
--      "EM_refPictureSelection">--
--<OSS.FIELDNAME
--      MULTIMEDIA-SYSTEM-CONTROL.H263Options.customPictureClockFrequency
--      "customPictureClockFrequency">--
--<OSS.DefineName
--      MULTIMEDIA-SYSTEM-CONTROL.H263Options.customPictureClockFrequency
--      "EM_customPictureClockFrequency">--
--<OSS.FIELDNAME
--      MULTIMEDIA-SYSTEM-CONTROL.H263Options.customPictureFormat
--      "customPictureFormat">--
--<OSS.DefineName
--      MULTIMEDIA-SYSTEM-CONTROL.H263Options.customPictureFormat
--      "EM_customPictureFormat">--
--<OSS.FIELDNAME
--      MULTIMEDIA-SYSTEM-CONTROL.H263Options.modeCombos
--      "modeCombos">--
--<OSS.DefineName
--      MULTIMEDIA-SYSTEM-CONTROL.H263Options.modeCombos
--      "EM_modeCombos">--

-- -------------------------------------------------------------- --
--
-- TransparencyParameters ::= SEQUENCE
-- {
--     presentationOrder               INTEGER(1..256),
--     offset-x                        INTEGER(-262144..262143),
--     offset-y                        INTEGER(-262144..262143),
--     scale-x                         INTEGER(1..255),
--     scale-y                         INTEGER(1..255),
--     ...
-- }
--
-- -------------------------------------------------------------- --

--<ASN1.PDU
--		MULTIMEDIA-SYSTEM-CONTROL.TransparencyParameters>--
--<OSS.TYPENAME
--		MULTIMEDIA-SYSTEM-CONTROL.TransparencyParameters
--		"EmTransparencyParameters">--
--<OSS.FIELDNAME
--		MULTIMEDIA-SYSTEM-CONTROL.TransparencyParameters.presentationOrder
--		"presentationOrder">--
--<OSS.FIELDNAME
--		MULTIMEDIA-SYSTEM-CONTROL.TransparencyParameters.offset-x
--		"offset_x">--
--<OSS.FIELDNAME
--		MULTIMEDIA-SYSTEM-CONTROL.TransparencyParameters.offset-y
--		"offset_y">--
--<OSS.FIELDNAME
--		MULTIMEDIA-SYSTEM-CONTROL.TransparencyParameters.scale-x
--		"scale_x">--
--<OSS.FIELDNAME
--		MULTIMEDIA-SYSTEM-CONTROL.TransparencyParameters.scale-y
--		"scale_y">--

-- -------------------------------------------------------------- --
--
-- RefPictureSelection ::= SEQUENCE
-- {
--     additionalPictureMemory SEQUENCE
--     {
--         sqcifAdditionalPictureMemory    INTEGER (1..256) OPTIONAL,
--         qcifAdditionalPictureMemory     INTEGER (1..256) OPTIONAL,
--         cifAdditionalPictureMemory      INTEGER (1..256) OPTIONAL,
--         cif4AdditionalPictureMemory     INTEGER (1..256) OPTIONAL,
--         cif16AdditionalPictureMemory    INTEGER (1..256) OPTIONAL,
--         bigCpfAdditionalPictureMemory   INTEGER (1..256) OPTIONAL,
--         ...
--     } OPTIONAL,
--     videoMux                BOOLEAN,
--     videoBackChannelSend    CHOICE
--     {
--         none                    NULL,
--         ackMessageOnly          NULL,
--         nackMessageOnly         NULL,
--         ackOrNackMessageOnly    NULL,
--         ackAndNackMessage       NULL,
--         ...
--     },
--     ...
-- }
--
-- -------------------------------------------------------------- --

--<ASN1.PDU
--		MULTIMEDIA-SYSTEM-CONTROL.RefPictureSelection>--
--<OSS.TYPENAME
--		MULTIMEDIA-SYSTEM-CONTROL.RefPictureSelection
--		"EmRefPictureSelection">--
--<OSS.InlineType
--		MULTIMEDIA-SYSTEM-CONTROL.RefPictureSelection.additionalPictureMemory>--
--<OSS.TYPENAME
--		MULTIMEDIA-SYSTEM-CONTROL.RefPictureSelection.additionalPictureMemory
--		"EmAdditionalPictureMemory">--
--<OSS.FIELDNAME
--		MULTIMEDIA-SYSTEM-CONTROL.RefPictureSelection.additionalPictureMemory
--		"additionalPictureMemory">--
--<OSS.DefineName
--		MULTIMEDIA-SYSTEM-CONTROL.RefPictureSelection.additionalPictureMemory
--		"EM_additionalPictureMemory">--
--<OSS.FIELDNAME
--		MULTIMEDIA-SYSTEM-CONTROL.RefPictureSelection.additionalPictureMemory.sqcifAdditionalPictureMemory
--		"sqcifAdditionalPictureMemory">--
--<OSS.DefineName
--		MULTIMEDIA-SYSTEM-CONTROL.RefPictureSelection.additionalPictureMemory.sqcifAdditionalPictureMemory
--		"EM_sqcifAdditionalPictureMemory">--
--<OSS.FIELDNAME
--		MULTIMEDIA-SYSTEM-CONTROL.RefPictureSelection.additionalPictureMemory.qcifAdditionalPictureMemory
--		"qcifAdditionalPictureMemory">--
--<OSS.DefineName
--		MULTIMEDIA-SYSTEM-CONTROL.RefPictureSelection.additionalPictureMemory.qcifAdditionalPictureMemory
--		"EM_qcifAdditionalPictureMemory">--
--<OSS.FIELDNAME
--		MULTIMEDIA-SYSTEM-CONTROL.RefPictureSelection.additionalPictureMemory.cifAdditionalPictureMemory
--		"cifAdditionalPictureMemory">--
--<OSS.DefineName
--		MULTIMEDIA-SYSTEM-CONTROL.RefPictureSelection.additionalPictureMemory.cifAdditionalPictureMemory
--		"EM_cifAdditionalPictureMemory">--
--<OSS.FIELDNAME
--		MULTIMEDIA-SYSTEM-CONTROL.RefPictureSelection.additionalPictureMemory.cif4AdditionalPictureMemory
--		"cif4AdditionalPictureMemory">--
--<OSS.DefineName
--		MULTIMEDIA-SYSTEM-CONTROL.RefPictureSelection.additionalPictureMemory.cif4AdditionalPictureMemory
--		"EM_cif4AdditionalPictureMemory">--
--<OSS.FIELDNAME
--		MULTIMEDIA-SYSTEM-CONTROL.RefPictureSelection.additionalPictureMemory.cif16AdditionalPictureMemory
--		"cif16AdditionalPictureMemory">--
--<OSS.DefineName
--		MULTIMEDIA-SYSTEM-CONTROL.RefPictureSelection.additionalPictureMemory.cif16AdditionalPictureMemory
--		"EM_cif16AdditionalPictureMemory">--
--<OSS.FIELDNAME
--		MULTIMEDIA-SYSTEM-CONTROL.RefPictureSelection.additionalPictureMemory.bigCpfAdditionalPictureMemory
--		"bigCpfAdditionalPictureMemory">--
--<OSS.DefineName
--		MULTIMEDIA-SYSTEM-CONTROL.RefPictureSelection.additionalPictureMemory.bigCpfAdditionalPictureMemory
--		"EM_bigCpfAdditionalPictureMemory">--
--<OSS.FIELDNAME
--		MULTIMEDIA-SYSTEM-CONTROL.RefPictureSelection.videoMux
--		"videoMux">--
--<OSS.FIELDNAME
--		MULTIMEDIA-SYSTEM-CONTROL.RefPictureSelection.videoBackChannelSend
--		"videoBackChannelSend">--
--<OSS.ExtractType
--		MULTIMEDIA-SYSTEM-CONTROL.RefPictureSelection.videoBackChannelSend>--
--<OSS.TYPENAME
--		MULTIMEDIA-SYSTEM-CONTROL.RefPictureSelection.videoBackChannelSend
--		"EmVideoBackChannelSend">--
--<OSS.FIELDNAME
--		MULTIMEDIA-SYSTEM-CONTROL.RefPictureSelection.videoBackChannelSend.none
--		"none">--
--<OSS.DefineName
--		MULTIMEDIA-SYSTEM-CONTROL.RefPictureSelection.videoBackChannelSend.none
--		"EM_VideoBackChannelSend_none">--
--<OSS.FIELDNAME
--		MULTIMEDIA-SYSTEM-CONTROL.RefPictureSelection.videoBackChannelSend.ackMessageOnly
--		"ackMessageOnly">--
--<OSS.DefineName
--		MULTIMEDIA-SYSTEM-CONTROL.RefPictureSelection.videoBackChannelSend.ackMessageOnly
--		"EM_ackMessageOnly">--
--<OSS.FIELDNAME
--		MULTIMEDIA-SYSTEM-CONTROL.RefPictureSelection.videoBackChannelSend.nackMessageOnly
--		"nackMessageOnly">--
--<OSS.DefineName
--		MULTIMEDIA-SYSTEM-CONTROL.RefPictureSelection.videoBackChannelSend.nackMessageOnly
--		"EM_nackMessageOnly">--
--<OSS.FIELDNAME
--		MULTIMEDIA-SYSTEM-CONTROL.RefPictureSelection.videoBackChannelSend.ackOrNackMessageOnly
--		"ackOrNackMessageOnly">--
--<OSS.DefineName
--		MULTIMEDIA-SYSTEM-CONTROL.RefPictureSelection.videoBackChannelSend.ackOrNackMessageOnly
--		"EM_ackOrNackMessageOnly">--
--<OSS.FIELDNAME
--		MULTIMEDIA-SYSTEM-CONTROL.RefPictureSelection.videoBackChannelSend.ackAndNackMessage
--		"ackAndNackMessage">--
--<OSS.DefineName
--		MULTIMEDIA-SYSTEM-CONTROL.RefPictureSelection.videoBackChannelSend.ackAndNackMessage
--		"EM_ackAndNackMessage">--

-- -------------------------------------------------------------- --
--
-- CustomPictureClockFrequency ::= SEQUENCE
-- {
--     clockConversionCode     INTEGER(1000..1001),
--     clockDivisor            INTEGER(1..127),
--     sqcifMPI                INTEGER(1..2048) OPTIONAL,
--     qcifMPI                 INTEGER(1..2048) OPTIONAL,
--     cifMPI                  INTEGER(1..2048) OPTIONAL,
--     cif4MPI                 INTEGER(1..2048) OPTIONAL,
--     cif16MPI                INTEGER(1..2048) OPTIONAL,
--     ...
-- }
--
-- -------------------------------------------------------------- --

--<ASN1.PDU
--		MULTIMEDIA-SYSTEM-CONTROL.CustomPictureClockFrequency>--
--<OSS.TYPENAME
--		MULTIMEDIA-SYSTEM-CONTROL.CustomPictureClockFrequency
--		"EmCustomPictureClockFrequency">--
--<OSS.FIELDNAME
--		MULTIMEDIA-SYSTEM-CONTROL.CustomPictureClockFrequency.clockConversionCode
--		"clockConversionCode">--
--<OSS.FIELDNAME
--		MULTIMEDIA-SYSTEM-CONTROL.CustomPictureClockFrequency.clockDivisor
--		"clockDivisor">--
--<OSS.FIELDNAME
--		MULTIMEDIA-SYSTEM-CONTROL.CustomPictureClockFrequency.sqcifMPI
--		"sqcifMPI">--
--<OSS.DefineName
--		MULTIMEDIA-SYSTEM-CONTROL.CustomPictureClockFrequency.sqcifMPI
--		"EM_CustomPictureClockFrequency_sqcifMPI">--
--<OSS.FIELDNAME
--		MULTIMEDIA-SYSTEM-CONTROL.CustomPictureClockFrequency.qcifMPI
--		"qcifMPI">--
--<OSS.DefineName
--		MULTIMEDIA-SYSTEM-CONTROL.CustomPictureClockFrequency.qcifMPI
--		"EM_CustomPictureClockFrequency_qcifMPI">--
--<OSS.FIELDNAME
--		MULTIMEDIA-SYSTEM-CONTROL.CustomPictureClockFrequency.cifMPI
--		"cifMPI">--
--<OSS.DefineName
--		MULTIMEDIA-SYSTEM-CONTROL.CustomPictureClockFrequency.cifMPI
--		"EM_CustomPictureClockFrequency_cifMPI">--
--<OSS.FIELDNAME
--		MULTIMEDIA-SYSTEM-CONTROL.CustomPictureClockFrequency.cif4MPI
--		"cif4MPI">--
--<OSS.DefineName
--		MULTIMEDIA-SYSTEM-CONTROL.CustomPictureClockFrequency.cif4MPI
--		"EM_CustomPictureClockFrequency_cif4MPI">--
--<OSS.FIELDNAME
--		MULTIMEDIA-SYSTEM-CONTROL.CustomPictureClockFrequency.cif16MPI
--		"cif16MPI">--
--<OSS.DefineName
--		MULTIMEDIA-SYSTEM-CONTROL.CustomPictureClockFrequency.cif16MPI
--		"EM_CustomPictureClockFrequency_cif16MPI">--

-- -------------------------------------------------------------- --
--
-- CustomPictureFormat ::= SEQUENCE
-- {
--     maxCustomPictureWidth   INTEGER(1..2048),
--     maxCustomPictureHeight  INTEGER(1..2048),
--     minCustomPictureWidth   INTEGER(1..2048),
--     minCustomPictureHeight  INTEGER(1..2048),
--     mPI         SEQUENCE
--     {
--         standardMPI INTEGER (1..31) OPTIONAL,
--         customPCF   SET SIZE (1..16) OF SEQUENCE
--         {
--             clockConversionCode INTEGER(1000..1001),
--             clockDivisor        INTEGER(1..127),
--             customMPI           INTEGER(1..2048),
--             ...
--         } OPTIONAL,
--         ...
--     },
--  
--     pixelAspectInformation  CHOICE
--     {
--         anyPixelAspectRatio BOOLEAN,
--         pixelAspectCode     SET SIZE (1..14) OF INTEGER(1..14),
--         extendedPAR         SET SIZE (1..256) OF SEQUENCE
--         {
--             width   INTEGER(1..255),
--             height  INTEGER(1..255),
--             ...
--         },
--         ...
--     },
--     ...
-- }
--
-- -------------------------------------------------------------- --

--<ASN1.PDU
--		MULTIMEDIA-SYSTEM-CONTROL.CustomPictureFormat>--
--<OSS.TYPENAME
--		MULTIMEDIA-SYSTEM-CONTROL.CustomPictureFormat
--		"EmCustomPictureFormat">--
--<OSS.FIELDNAME
--		MULTIMEDIA-SYSTEM-CONTROL.CustomPictureFormat.maxCustomPictureWidth
--		"maxCustomPictureWidth">--
--<OSS.FIELDNAME
--		MULTIMEDIA-SYSTEM-CONTROL.CustomPictureFormat.maxCustomPictureHeight
--		"maxCustomPictureHeight">--
--<OSS.FIELDNAME
--		MULTIMEDIA-SYSTEM-CONTROL.CustomPictureFormat.minCustomPictureWidth
--		"minCustomPictureWidth">--
--<OSS.FIELDNAME
--		MULTIMEDIA-SYSTEM-CONTROL.CustomPictureFormat.minCustomPictureHeight
--		"minCustomPictureHeight">--
--<OSS.InlineType
--		MULTIMEDIA-SYSTEM-CONTROL.CustomPictureFormat.mPI>--
--<OSS.TYPENAME
--		MULTIMEDIA-SYSTEM-CONTROL.CustomPictureFormat.mPI
--		"EmMPI">--
--<OSS.FIELDNAME
--		MULTIMEDIA-SYSTEM-CONTROL.CustomPictureFormat.mPI
--		"mPI">--
--<OSS.FIELDNAME
--		MULTIMEDIA-SYSTEM-CONTROL.CustomPictureFormat.mPI.standardMPI
--		"standardMPI">--
--<OSS.DefineName
--		MULTIMEDIA-SYSTEM-CONTROL.CustomPictureFormat.mPI.standardMPI
--		"EM_standardMPI">--
--<OSS.InlineType
--		MULTIMEDIA-SYSTEM-CONTROL.CustomPictureFormat.mPI.customPCF>--
--<OSS.TYPENAME
--		MULTIMEDIA-SYSTEM-CONTROL.CustomPictureFormat.mPI.customPCF
--		"EmCustomPCF">--
--<OSS.FIELDNAME
--		MULTIMEDIA-SYSTEM-CONTROL.CustomPictureFormat.mPI.customPCF
--		"customPCF">--
--<OSS.DefineName
--		MULTIMEDIA-SYSTEM-CONTROL.CustomPictureFormat.mPI.customPCF
--		"EM_customPCF">--
--<OSS.TYPENAME
--		MULTIMEDIA-SYSTEM-CONTROL.CustomPictureFormat.mPI.customPCF.*
--		"EmSeqOfCustomPCF">--
--<OSS.FIELDNAME
--		MULTIMEDIA-SYSTEM-CONTROL.CustomPictureFormat.mPI.customPCF.*.clockConversionCode
--		"clockConversionCode">--
--<OSS.FIELDNAME
--		MULTIMEDIA-SYSTEM-CONTROL.CustomPictureFormat.mPI.customPCF.*.clockDivisor
--		"clockDivisor">--
--<OSS.FIELDNAME
--		MULTIMEDIA-SYSTEM-CONTROL.CustomPictureFormat.mPI.customPCF.*.customMPI
--		"customMPI">--
--<OSS.ExtractType
--		MULTIMEDIA-SYSTEM-CONTROL.CustomPictureFormat.pixelAspectInformation.anyPixelAspectRatio>--
--<OSS.TYPENAME
--		MULTIMEDIA-SYSTEM-CONTROL.CustomPictureFormat.pixelAspectInformation
--		"EmPixelAspectInformation">--
--<OSS.FIELDNAME
--		MULTIMEDIA-SYSTEM-CONTROL.CustomPictureFormat.pixelAspectInformation
--		"pixelAspectInformation">--
--<OSS.FIELDNAME
--		MULTIMEDIA-SYSTEM-CONTROL.CustomPictureFormat.pixelAspectInformation.anyPixelAspectRatio
--		"anyPixelAspectRatio">--
--<OSS.DefineName
--		MULTIMEDIA-SYSTEM-CONTROL.CustomPictureFormat.pixelAspectInformation.anyPixelAspectRatio
--		"EM_anyPixelAspectRatio">--
--<OSS.FIELDNAME
--		MULTIMEDIA-SYSTEM-CONTROL.CustomPictureFormat.pixelAspectInformation.pixelAspectCode
--		"pixelAspectCode">--
--<OSS.DefineName
--		MULTIMEDIA-SYSTEM-CONTROL.CustomPictureFormat.pixelAspectInformation.pixelAspectCode
--		"EM_pixelAspectCode">--
--<OSS.FIELDNAME
--		MULTIMEDIA-SYSTEM-CONTROL.CustomPictureFormat.pixelAspectInformation.extendedPAR
--		"extendedPAR">--
--<OSS.DefineName
--		MULTIMEDIA-SYSTEM-CONTROL.CustomPictureFormat.pixelAspectInformation.extendedPAR
--		"EM_extendedPAR">--
--<OSS.TYPENAME
--		MULTIMEDIA-SYSTEM-CONTROL.CustomPictureFormat.pixelAspectInformation.extendedPAR
--		"EmSetOfExtendedPAR">--
--<OSS.TYPENAME
--		MULTIMEDIA-SYSTEM-CONTROL.CustomPictureFormat.pixelAspectInformation.extendedPAR.*
--		"EmExtendedPAR">--
--<OSS.FIELDNAME
--		MULTIMEDIA-SYSTEM-CONTROL.CustomPictureFormat.pixelAspectInformation.extendedPAR.*.width
--		"width">--
--<OSS.FIELDNAME
--		MULTIMEDIA-SYSTEM-CONTROL.CustomPictureFormat.pixelAspectInformation.extendedPAR.*.height
--		"height">--

-- -------------------------------------------------------------- --
--
-- H263VideoModeCombos ::= SEQUENCE
-- {
--     h263VideoUncoupledModes H263ModeComboFlags,
--     h263VideoCoupledModes   SET SIZE (1..16) OF H263ModeComboFlags,
--     ...
-- }
--
-- -------------------------------------------------------------- --

--<ASN1.PDU
--		MULTIMEDIA-SYSTEM-CONTROL.H263VideoModeCombos>--
--<OSS.TYPENAME
--		MULTIMEDIA-SYSTEM-CONTROL.H263VideoModeCombos
--		"EmH263VideoModeCombos">--
--<OSS.FIELDNAME
--		MULTIMEDIA-SYSTEM-CONTROL.H263VideoModeCombos.h263VideoUncoupledModes
--		"h263VideoUncoupledModes">--
--<OSS.FIELDNAME
--		MULTIMEDIA-SYSTEM-CONTROL.H263VideoModeCombos.h263VideoCoupledModes
--		"h263VideoCoupledModes">--

-- -------------------------------------------------------------- --
--
-- H263ModeComboFlags ::= SEQUENCE
-- {
--     unrestrictedVector                  BOOLEAN,
--     arithmeticCoding                    BOOLEAN,
--     advancedPrediction                  BOOLEAN,
--     pbFrames                            BOOLEAN,
--     advancedIntraCodingMode             BOOLEAN,
--     deblockingFilterMode                BOOLEAN,
--     unlimitedMotionVectors              BOOLEAN,
--     slicesInOrder-NonRect               BOOLEAN,
--     slicesInOrder-Rect                  BOOLEAN,
--     slicesNoOrder-NonRect               BOOLEAN,
--     slicesNoOrder-Rect                  BOOLEAN,
--     improvedPBFramesMode                BOOLEAN,
--     referencePicSelect                  BOOLEAN,
--     dynamicPictureResizingByFour        BOOLEAN,
--     dynamicPictureResizingSixteenthPel  BOOLEAN,
--     dynamicWarpingHalfPel               BOOLEAN,
--     dynamicWarpingSixteenthPel          BOOLEAN,
--     reducedResolutionUpdate             BOOLEAN,
--     independentSegmentDecoding          BOOLEAN,
--     alternateInterVLCMode               BOOLEAN,
--     modifiedQuantizationMode            BOOLEAN,
--     ...
-- }
-- 
-- -------------------------------------------------------------- --

--<ASN1.PDU
--		MULTIMEDIA-SYSTEM-CONTROL.H263ModeComboFlags>--
--<OSS.TYPENAME
--		MULTIMEDIA-SYSTEM-CONTROL.H263ModeComboFlags
--		"EmH263ModeComboFlags">--
--<OSS.FIELDNAME
--      MULTIMEDIA-SYSTEM-CONTROL.H263ModeComboFlags.unrestrictedVector
--      "unrestrictedVector">--
--<OSS.FIELDNAME
--      MULTIMEDIA-SYSTEM-CONTROL.H263ModeComboFlags.arithmeticCoding
--      "arithmeticCoding">--
--<OSS.FIELDNAME
--      MULTIMEDIA-SYSTEM-CONTROL.H263ModeComboFlags.advancedPrediction
--      "advancedPrediction">--
--<OSS.FIELDNAME
--      MULTIMEDIA-SYSTEM-CONTROL.H263ModeComboFlags.pbFrames
--      "pbFrames">--
--<OSS.FIELDNAME
--      MULTIMEDIA-SYSTEM-CONTROL.H263ModeComboFlags.advancedIntraCodingMode
--      "advancedIntraCodingMode">--
--<OSS.FIELDNAME
--      MULTIMEDIA-SYSTEM-CONTROL.H263ModeComboFlags.deblockingFilterMode
--      "deblockingFilterMode">--
--<OSS.FIELDNAME
--      MULTIMEDIA-SYSTEM-CONTROL.H263ModeComboFlags.unlimitedMotionVectors
--      "unlimitedMotionVectors">--
--<OSS.FIELDNAME
--      MULTIMEDIA-SYSTEM-CONTROL.H263ModeComboFlags.slicesInOrder-NonRect
--      "slicesInOrder_NonRect">--
--<OSS.FIELDNAME
--      MULTIMEDIA-SYSTEM-CONTROL.H263ModeComboFlags.slicesInOrder-Rect
--      "slicesInOrder_Rect">--
--<OSS.FIELDNAME
--      MULTIMEDIA-SYSTEM-CONTROL.H263ModeComboFlags.slicesNoOrder-NonRect
--      "slicesNoOrder_NonRect">--
--<OSS.FIELDNAME
--      MULTIMEDIA-SYSTEM-CONTROL.H263ModeComboFlags.slicesNoOrder-Rect
--      "slicesNoOrder_Rect">--
--<OSS.FIELDNAME
--      MULTIMEDIA-SYSTEM-CONTROL.H263ModeComboFlags.improvedPBFramesMode
--      "improvedPBFramesMode">--
--<OSS.FIELDNAME
--      MULTIMEDIA-SYSTEM-CONTROL.H263ModeComboFlags.referencePicSelect
--      "referencePicSelect">--
--<OSS.FIELDNAME
--      MULTIMEDIA-SYSTEM-CONTROL.H263ModeComboFlags.dynamicPictureResizingByFour
--      "dynamicPictureResizingByFour">--
--<OSS.FIELDNAME
--      MULTIMEDIA-SYSTEM-CONTROL.H263ModeComboFlags.dynamicPictureResizingSixteenthPel
--      "dynamicPictureResizingSixteenthPel">--
--<OSS.FIELDNAME
--      MULTIMEDIA-SYSTEM-CONTROL.H263ModeComboFlags.dynamicWarpingHalfPel
--      "dynamicWarpingHalfPel">--
--<OSS.FIELDNAME
--      MULTIMEDIA-SYSTEM-CONTROL.H263ModeComboFlags.dynamicWarpingSixteenthPel
--      "dynamicWarpingSixteenthPel">--
--<OSS.FIELDNAME
--      MULTIMEDIA-SYSTEM-CONTROL.H263ModeComboFlags.reducedResolutionUpdate
--      "reducedResolutionUpdate">--
--<OSS.FIELDNAME
--      MULTIMEDIA-SYSTEM-CONTROL.H263ModeComboFlags.independentSegmentDecoding
--      "independentSegmentDecoding">--
--<OSS.FIELDNAME
--      MULTIMEDIA-SYSTEM-CONTROL.H263ModeComboFlags.alternateInterVLCMode
--      "alternateInterVLCMode">--
--<OSS.FIELDNAME
--      MULTIMEDIA-SYSTEM-CONTROL.H263ModeComboFlags.modifiedQuantizationMode
--      "modifiedQuantizationMode">--

-- -------------------------------------------------------------- --
--  
-- IS11172VideoCapability  ::= SEQUENCE
-- {
--     constrainedBitstream    BOOLEAN,
--     videoBitRate            INTEGER (0.. 1073741823)  OPTIONAL,
--     vbvBufferSize           INTEGER (0.. 262143)  OPTIONAL,
--     samplesPerLine          INTEGER (0..16383)  OPTIONAL,
--     linesPerFrame           INTEGER (0..16383)  OPTIONAL,
--     pictureRate             INTEGER (0..15)  OPTIONAL,
--     luminanceSampleRate     INTEGER (0..4294967295)  OPTIONAL,
--     ...
-- }
-- 
-- -------------------------------------------------------------- --

--<ASN1.PDU
--		MULTIMEDIA-SYSTEM-CONTROL.IS11172VideoCapability>--
--<OSS.TYPENAME
--		MULTIMEDIA-SYSTEM-CONTROL.IS11172VideoCapability
--		"EmIS11172VideoCapability">--
--<OSS.FIELDNAME
--		MULTIMEDIA-SYSTEM-CONTROL.IS11172VideoCapability.constrainedBitstream
--		"constrainedBitstream">--
--<OSS.FIELDNAME
--		MULTIMEDIA-SYSTEM-CONTROL.IS11172VideoCapability.videoBitRate
--		"videoBitRate">--
--<OSS.DefineName
--		MULTIMEDIA-SYSTEM-CONTROL.IS11172VideoCapability.videoBitRate
--		"EM_IS11172VideoCapability_videoBitRate">--
--<OSS.FIELDNAME
--		MULTIMEDIA-SYSTEM-CONTROL.IS11172VideoCapability.vbvBufferSize
--		"vbvBufferSize">--
--<OSS.DefineName
--		MULTIMEDIA-SYSTEM-CONTROL.IS11172VideoCapability.vbvBufferSize
--		"EM_IS11172VideoCapability_vbvBufferSize">--
--<OSS.FIELDNAME
--		MULTIMEDIA-SYSTEM-CONTROL.IS11172VideoCapability.samplesPerLine
--		"samplesPerLine">--
--<OSS.DefineName
--		MULTIMEDIA-SYSTEM-CONTROL.IS11172VideoCapability.samplesPerLine
--		"EM_IS11172VideoCapability_samplesPerLine">--
--<OSS.FIELDNAME
--		MULTIMEDIA-SYSTEM-CONTROL.IS11172VideoCapability.linesPerFrame
--		"linesPerFrame">--
--<OSS.DefineName
--		MULTIMEDIA-SYSTEM-CONTROL.IS11172VideoCapability.linesPerFrame
--		"EM_IS11172VideoCapability_linesPerFrame">--
--<OSS.FIELDNAME
--		MULTIMEDIA-SYSTEM-CONTROL.IS11172VideoCapability.pictureRate
--		"pictureRate">--
--<OSS.DefineName
--		MULTIMEDIA-SYSTEM-CONTROL.IS11172VideoCapability.pictureRate
--		"EM_IS11172VideoCapability_pictureRate">--
--<OSS.FIELDNAME
--		MULTIMEDIA-SYSTEM-CONTROL.IS11172VideoCapability.luminanceSampleRate
--		"luminanceSampleRate">--
--<OSS.DefineName
--		MULTIMEDIA-SYSTEM-CONTROL.IS11172VideoCapability.luminanceSampleRate
--		"EM_IS11172VideoCapability_luminanceSampleRate">--

-- ==============================================================
-- Capability exchange definitions: Audio capabilities
-- ==============================================================

-- -------------------------------------------------------------- --
--
-- AudioCapability ::= CHOICE
-- {
--     nonStandard             NonStandardParameter,
--     g711Alaw64k             INTEGER (1..256),
--     g711Alaw56k             INTEGER (1..256),
--     g711Ulaw64k             INTEGER (1..256),
--     g711Ulaw56k             INTEGER (1..256),
--  
--     g722-64k                INTEGER (1..256),
--     g722-56k                INTEGER (1..256),
--     g722-48k                INTEGER (1..256),
--  
--     g7231       SEQUENCE
--     {
--         maxAl-sduAudioFrames    INTEGER (1..256),
--         silenceSuppression      BOOLEAN
--     },
--        
--  
--     g728                    INTEGER (1..256),
--     g729                    INTEGER (1..256),
--     g729AnnexA              INTEGER (1..256),
--     is11172AudioCapability  IS11172AudioCapability,
--     is13818AudioCapability  IS13818AudioCapability,
--      ...,
--     g729wAnnexB             INTEGER(1..256),
--     g729AnnexAwAnnexB       INTEGER(1..256),
--     g7231AnnexCCapability   G7231AnnexCCapability,
--     gsmFullRate             GSMAudioCapability,
--     gsmHalfRate             GSMAudioCapability,
--     gsmEnhancedFullRate     GSMAudioCapability
-- }
--  
--
-- -------------------------------------------------------------- --

--<ASN1.PDU
--		MULTIMEDIA-SYSTEM-CONTROL.AudioCapability>--
--<OSS.TYPENAME
--		MULTIMEDIA-SYSTEM-CONTROL.AudioCapability
--		"EmAudioCapability">--
--<OSS.FIELDNAME
--		MULTIMEDIA-SYSTEM-CONTROL.AudioCapability.nonStandard
--		"nonStandard">--
--<OSS.DefineName
--		MULTIMEDIA-SYSTEM-CONTROL.AudioCapability.nonStandard
--		"EM_AudioCapability_nonStandard">--
--<OSS.FIELDNAME
--		MULTIMEDIA-SYSTEM-CONTROL.AudioCapability.g711Alaw64k
--		"g711Alaw64k">--
--<OSS.DefineName
--		MULTIMEDIA-SYSTEM-CONTROL.AudioCapability.g711Alaw64k
--		"EM_AudioCapability_g711Alaw64k">--
--<OSS.FIELDNAME
--		MULTIMEDIA-SYSTEM-CONTROL.AudioCapability.g711Alaw56k
--		"g711Alaw56k">--
--<OSS.DefineName
--		MULTIMEDIA-SYSTEM-CONTROL.AudioCapability.g711Alaw56k
--		"EM_AudioCapability_g711Alaw56k">--
--<OSS.FIELDNAME
--		MULTIMEDIA-SYSTEM-CONTROL.AudioCapability.g711Ulaw64k
--		"g711Ulaw64k">--
--<OSS.DefineName
--		MULTIMEDIA-SYSTEM-CONTROL.AudioCapability.g711Ulaw64k
--		"EM_AudioCapability_g711Ulaw64k">--
--<OSS.FIELDNAME
--		MULTIMEDIA-SYSTEM-CONTROL.AudioCapability.g711Ulaw56k
--		"g711Ulaw56k">--
--<OSS.DefineName
--		MULTIMEDIA-SYSTEM-CONTROL.AudioCapability.g711Ulaw56k
--		"EM_AudioCapability_g711Ulaw56k">--
--<OSS.FIELDNAME
--		MULTIMEDIA-SYSTEM-CONTROL.AudioCapability.g722-64k
--		"g722_64k">--
--<OSS.DefineName
--		MULTIMEDIA-SYSTEM-CONTROL.AudioCapability.g722-64k
--		"EM_AudioCapability_g722_64k">--
--<OSS.FIELDNAME
--		MULTIMEDIA-SYSTEM-CONTROL.AudioCapability.g722-56k
--		"g722_56k">--
--<OSS.DefineName
--		MULTIMEDIA-SYSTEM-CONTROL.AudioCapability.g722-56k
--		"EM_AudioCapability_g722_56k">--
--<OSS.FIELDNAME
--		MULTIMEDIA-SYSTEM-CONTROL.AudioCapability.g722-48k
--		"g722_48k">--
--<OSS.DefineName
--		MULTIMEDIA-SYSTEM-CONTROL.AudioCapability.g722-48k
--		"EM_AudioCapability_g722_48k">--
--<OSS.InlineType
--		MULTIMEDIA-SYSTEM-CONTROL.AudioCapability.g7231>--
--<OSS.TYPENAME
--		MULTIMEDIA-SYSTEM-CONTROL.AudioCapability.g7231
--		"EmG7231">--
--<OSS.FIELDNAME
--		MULTIMEDIA-SYSTEM-CONTROL.AudioCapability.g7231
--		"g7231">--
--<OSS.DefineName
--		MULTIMEDIA-SYSTEM-CONTROL.AudioCapability.g7231
--		"EM_AudioCapability_g7231">--
--<OSS.FIELDNAME
--		MULTIMEDIA-SYSTEM-CONTROL.AudioCapability.g7231.maxAl-sduAudioFrames
--		"maxAl_sduAudioFrames">--
--<OSS.FIELDNAME
--		MULTIMEDIA-SYSTEM-CONTROL.AudioCapability.g7231.silenceSuppression
--		"silenceSuppression">--
--<OSS.FIELDNAME
--		MULTIMEDIA-SYSTEM-CONTROL.AudioCapability.g728
--		"g728">--
--<OSS.DefineName
--		MULTIMEDIA-SYSTEM-CONTROL.AudioCapability.g728
--		"EM_AudioCapability_g728">--
--<OSS.FIELDNAME
--		MULTIMEDIA-SYSTEM-CONTROL.AudioCapability.g729
--		"g729">--
--<OSS.DefineName
--		MULTIMEDIA-SYSTEM-CONTROL.AudioCapability.g729
--		"EM_AudioCapability_g729">--
--<OSS.FIELDNAME
--		MULTIMEDIA-SYSTEM-CONTROL.AudioCapability.g729AnnexA
--		"g729AnnexA">--
--<OSS.DefineName
--		MULTIMEDIA-SYSTEM-CONTROL.AudioCapability.g729AnnexA
--		"EM_AudioCapability_g729AnnexA">--
--<OSS.FIELDNAME
--		MULTIMEDIA-SYSTEM-CONTROL.AudioCapability.is11172AudioCapability
--		"is11172AudioCapability">--
--<OSS.DefineName
--		MULTIMEDIA-SYSTEM-CONTROL.AudioCapability.is11172AudioCapability
--		"EM_is11172AudioCapability">--
--<OSS.FIELDNAME
--		MULTIMEDIA-SYSTEM-CONTROL.AudioCapability.is13818AudioCapability
--		"is13818AudioCapability">--
--<OSS.DefineName
--		MULTIMEDIA-SYSTEM-CONTROL.AudioCapability.is13818AudioCapability
--		"EM_is13818AudioCapability">--
--<OSS.FIELDNAME
--		MULTIMEDIA-SYSTEM-CONTROL.AudioCapability.g729wAnnexB
--		"g729wAnnexB">--
--<OSS.DefineName
--		MULTIMEDIA-SYSTEM-CONTROL.AudioCapability.g729wAnnexB
--		"EM_AudioCapability_g729wAnnexB">--
--<OSS.FIELDNAME
--		MULTIMEDIA-SYSTEM-CONTROL.AudioCapability.g729AnnexAwAnnexB
--		"g729AnnexAwAnnexB">--
--<OSS.DefineName
--		MULTIMEDIA-SYSTEM-CONTROL.AudioCapability.g729AnnexAwAnnexB
--		"EM_AudioCapability_g729AnnexAwAnnexB">--
--<OSS.FIELDNAME
--		MULTIMEDIA-SYSTEM-CONTROL.AudioCapability.g7231AnnexCCapability
--		"g7231AnnexCCapability">--
--<OSS.DefineName
--		MULTIMEDIA-SYSTEM-CONTROL.AudioCapability.g7231AnnexCCapability
--		"EM_AudioCapability_g7231AnnexCCapability">--
--<OSS.FIELDNAME
--		MULTIMEDIA-SYSTEM-CONTROL.AudioCapability.gsmFullRate
--		"gsmFullRate">--
--<OSS.DefineName
--		MULTIMEDIA-SYSTEM-CONTROL.AudioCapability.gsmFullRate
--		"EM_AudioCapability_gsmFullRate">--
--<OSS.FIELDNAME
--		MULTIMEDIA-SYSTEM-CONTROL.AudioCapability.gsmHalfRate
--		"gsmHalfRate">--
--<OSS.DefineName
--		MULTIMEDIA-SYSTEM-CONTROL.AudioCapability.gsmHalfRate
--		"EM_AudioCapability_gsmHalfRate">--
--<OSS.FIELDNAME
--		MULTIMEDIA-SYSTEM-CONTROL.AudioCapability.gsmEnhancedFullRate
--		"gsmEnhancedFullRate">--
--<OSS.DefineName
--		MULTIMEDIA-SYSTEM-CONTROL.AudioCapability.gsmEnhancedFullRate
--		"EM_AudioCapability_gsmEnhancedFullRate">--

-- -------------------------------------------------------------- --
--
-- G723AnnexCAudioMode ::= SEQUENCE
-- {
-- 	highRateMode0	INTEGER (27..78),	
-- 	highRateMode1	INTEGER (27..78),	
-- 	lowRateMode0	INTEGER (23..66),	
-- 	lowRateMode1	INTEGER (23..66),	
-- 	sidMode0		INTEGER (6..17),	
-- 	sidMode1		INTEGER (6..17),	
-- 	...
-- }
-- 
-- -------------------------------------------------------------- --

--<ASN1.PDU
--      MULTIMEDIA-SYSTEM-CONTROL.G723AnnexCAudioMode>--
--<OSS.TYPENAME
--      MULTIMEDIA-SYSTEM-CONTROL.G723AnnexCAudioMode
--		"EmG723AnnexCAudioMode">--
--<OSS.FIELDNAME
--      MULTIMEDIA-SYSTEM-CONTROL.G723AnnexCAudioMode.highRateMode0
--      "highRateMode0">--
--<OSS.FIELDNAME
--      MULTIMEDIA-SYSTEM-CONTROL.G723AnnexCAudioMode.highRateMode1
--      "highRateMode1">--
--<OSS.FIELDNAME
--      MULTIMEDIA-SYSTEM-CONTROL.G723AnnexCAudioMode.lowRateMode0
--      "lowRateMode0">--
--<OSS.FIELDNAME
--      MULTIMEDIA-SYSTEM-CONTROL.G723AnnexCAudioMode.lowRateMode1
--      "lowRateMode1">--
--<OSS.FIELDNAME
--      MULTIMEDIA-SYSTEM-CONTROL.G723AnnexCAudioMode.sidMode0
--      "sidMode0">--
--<OSS.FIELDNAME
--      MULTIMEDIA-SYSTEM-CONTROL.G723AnnexCAudioMode.sidMode1
--      "sidMode1">--

-- -------------------------------------------------------------- --
-- 
-- G7231AnnexCCapability	::= SEQUENCE
-- {
-- 	maxAl-sduAudioFrames	INTEGER (1..256),
-- 	silenceSuppression		BOOLEAN,
-- 	g723AnnexCAudioMode	 	G723AnnexCAudioMode OPTIONAL,
-- 	...
-- }
-- 
-- -------------------------------------------------------------- --

--<ASN1.PDU
--		MULTIMEDIA-SYSTEM-CONTROL.G7231AnnexCCapability>--
--<OSS.TYPENAME
--		MULTIMEDIA-SYSTEM-CONTROL.G7231AnnexCCapability
--		"EmG7231AnnexCCapability">--
--<OSS.FIELDNAME
--		MULTIMEDIA-SYSTEM-CONTROL.G7231AnnexCCapability.maxAl-sduAudioFrames
--		"maxAl_sduAudioFrames">--
--<OSS.FIELDNAME
--		MULTIMEDIA-SYSTEM-CONTROL.G7231AnnexCCapability.silenceSuppression
--		"silenceSuppression">--
--<OSS.FIELDNAME
--		MULTIMEDIA-SYSTEM-CONTROL.G7231AnnexCCapability.g723AnnexCAudioMode
--		"g723AnnexCAudioMode">--
--<OSS.DefineName
--		MULTIMEDIA-SYSTEM-CONTROL.G7231AnnexCCapability.g723AnnexCAudioMode
--		"EM_g723AnnexCAudioMode">--

-- -------------------------------------------------------------- --
--
-- IS11172AudioCapability  ::= SEQUENCE
-- {
--     audioLayer1         BOOLEAN,
--     audioLayer2         BOOLEAN,
--     audioLayer3         BOOLEAN,
--  
--     audioSampling32k    BOOLEAN,
--     audioSampling44k1   BOOLEAN,
--     audioSampling48k    BOOLEAN,
--  
--     singleChannel       BOOLEAN,
--     twoChannels         BOOLEAN,
--  
--     bitRate             INTEGER (1..448),
--     ...
-- }
-- 
-- -------------------------------------------------------------- --

--<ASN1.PDU
--		MULTIMEDIA-SYSTEM-CONTROL.IS11172AudioCapability>--
--<OSS.TYPENAME
--		MULTIMEDIA-SYSTEM-CONTROL.IS11172AudioCapability
--		"EmIS11172AudioCapability">--
--<OSS.FIELDNAME
--		MULTIMEDIA-SYSTEM-CONTROL.IS11172AudioCapability.audioLayer1
--		"audioLayer1">--
--<OSS.FIELDNAME
--		MULTIMEDIA-SYSTEM-CONTROL.IS11172AudioCapability.audioLayer2
--		"audioLayer2">--
--<OSS.FIELDNAME
--		MULTIMEDIA-SYSTEM-CONTROL.IS11172AudioCapability.audioLayer3
--		"audioLayer3">--
--<OSS.FIELDNAME
--		MULTIMEDIA-SYSTEM-CONTROL.IS11172AudioCapability.audioSampling32k
--		"audioSampling32k">--
--<OSS.FIELDNAME
--		MULTIMEDIA-SYSTEM-CONTROL.IS11172AudioCapability.audioSampling44k1
--		"audioSampling44k1">--
--<OSS.FIELDNAME
--		MULTIMEDIA-SYSTEM-CONTROL.IS11172AudioCapability.audioSampling48k
--		"audioSampling48k">--
--<OSS.FIELDNAME
--		MULTIMEDIA-SYSTEM-CONTROL.IS11172AudioCapability.singleChannel
--		"singleChannel">--
--<OSS.FIELDNAME
--		MULTIMEDIA-SYSTEM-CONTROL.IS11172AudioCapability.twoChannels
--		"twoChannels">--
--<OSS.FIELDNAME
--		MULTIMEDIA-SYSTEM-CONTROL.IS11172AudioCapability.bitRate
--		"bitRate">--

-- -------------------------------------------------------------- --
--  
-- IS13818AudioCapability  ::= SEQUENCE
-- {
--     audioLayer1             BOOLEAN,
--     audioLayer2             BOOLEAN,
--     audioLayer3             BOOLEAN,
--  
--     audioSampling16k        BOOLEAN,
--     audioSampling22k05      BOOLEAN,
--     audioSampling24k        BOOLEAN,
--     audioSampling32k        BOOLEAN,
--     audioSampling44k1       BOOLEAN,
--     audioSampling48k        BOOLEAN,
--  
--     singleChannel           BOOLEAN,
--     twoChannels             BOOLEAN,
--     threeChannels2-1        BOOLEAN,
--     threeChannels3-0        BOOLEAN,
--     fourChannels2-0-2-0     BOOLEAN,
--     fourChannels2-2         BOOLEAN,
--     fourChannels3-1         BOOLEAN,
--     fiveChannels3-0-2-0     BOOLEAN,
--     fiveChannels3-2         BOOLEAN,
--  
--     lowFrequencyEnhancement BOOLEAN,
--  
--     multilingual            BOOLEAN,
--  
--     bitRate                 INTEGER (1..1130),
--     ...
-- }
--
-- -------------------------------------------------------------- --

--<ASN1.PDU
--		MULTIMEDIA-SYSTEM-CONTROL.IS13818AudioCapability>--
--<OSS.TYPENAME
--		MULTIMEDIA-SYSTEM-CONTROL.IS13818AudioCapability
--		"EmIS13818AudioCapability">--
--<OSS.FIELDNAME
--		MULTIMEDIA-SYSTEM-CONTROL.IS13818AudioCapability.audioLayer1
--		"audioLayer1">--
--<OSS.FIELDNAME
--		MULTIMEDIA-SYSTEM-CONTROL.IS13818AudioCapability.audioLayer2
--		"audioLayer2">--
--<OSS.FIELDNAME
--		MULTIMEDIA-SYSTEM-CONTROL.IS13818AudioCapability.audioLayer3
--		"audioLayer3">--
--<OSS.FIELDNAME
--		MULTIMEDIA-SYSTEM-CONTROL.IS13818AudioCapability.audioSampling16k
--		"audioSampling16k">--
--<OSS.FIELDNAME
--		MULTIMEDIA-SYSTEM-CONTROL.IS13818AudioCapability.audioSampling22k05
--		"audioSampling22k05">--
--<OSS.FIELDNAME
--		MULTIMEDIA-SYSTEM-CONTROL.IS13818AudioCapability.audioSampling24k
--		"audioSampling24k">--
--<OSS.FIELDNAME
--		MULTIMEDIA-SYSTEM-CONTROL.IS13818AudioCapability.audioSampling32k
--		"audioSampling32k">--
--<OSS.FIELDNAME
--		MULTIMEDIA-SYSTEM-CONTROL.IS13818AudioCapability.audioSampling44k1
--		"audioSampling44k1">--
--<OSS.FIELDNAME
--		MULTIMEDIA-SYSTEM-CONTROL.IS13818AudioCapability.audioSampling48k
--		"audioSampling48k">--
--<OSS.FIELDNAME
--		MULTIMEDIA-SYSTEM-CONTROL.IS13818AudioCapability.singleChannel
--		"singleChannel">--
--<OSS.FIELDNAME
--		MULTIMEDIA-SYSTEM-CONTROL.IS13818AudioCapability.twoChannels
--		"twoChannels">--
--<OSS.FIELDNAME
--		MULTIMEDIA-SYSTEM-CONTROL.IS13818AudioCapability.threeChannels2-1
--		"threeChannels2_1">--
--<OSS.FIELDNAME
--		MULTIMEDIA-SYSTEM-CONTROL.IS13818AudioCapability.threeChannels3-0
--		"threeChannels3_0">--
--<OSS.FIELDNAME
--		MULTIMEDIA-SYSTEM-CONTROL.IS13818AudioCapability.fourChannels2-0-2-0
--		"fourChannels2_0_2_0">--
--<OSS.FIELDNAME
--		MULTIMEDIA-SYSTEM-CONTROL.IS13818AudioCapability.fourChannels2-2
--		"fourChannels2_2">--
--<OSS.FIELDNAME
--		MULTIMEDIA-SYSTEM-CONTROL.IS13818AudioCapability.fourChannels3-1
--		"fourChannels3_1">--
--<OSS.FIELDNAME
--		MULTIMEDIA-SYSTEM-CONTROL.IS13818AudioCapability.fiveChannels3-0-2-0
--		"fiveChannels3_0_2_0">--
--<OSS.FIELDNAME
--		MULTIMEDIA-SYSTEM-CONTROL.IS13818AudioCapability.fiveChannels3-2
--		"fiveChannels3_2">--
--<OSS.FIELDNAME
--		MULTIMEDIA-SYSTEM-CONTROL.IS13818AudioCapability.lowFrequencyEnhancement
--		"lowFrequencyEnhancement">--
--<OSS.FIELDNAME
--		MULTIMEDIA-SYSTEM-CONTROL.IS13818AudioCapability.multilingual
--		"multilingual">--
--<OSS.FIELDNAME
--		MULTIMEDIA-SYSTEM-CONTROL.IS13818AudioCapability.bitRate
--		"bitRate">--

-- -------------------------------------------------------------- --
--
-- GSMAudioCapability ::= SEQUENCE
-- {
--     audioUnitSize   INTEGER (1..256),
--     comfortNoise    BOOLEAN,
--     scrambled       BOOLEAN,
--     ...
-- }
--
-- -------------------------------------------------------------- --

--<ASN1.PDU
--		MULTIMEDIA-SYSTEM-CONTROL.GSMAudioCapability>--
--<OSS.TYPENAME
--		MULTIMEDIA-SYSTEM-CONTROL.GSMAudioCapability
--		"EmGSMAudioCapability">--
--<OSS.FIELDNAME
--		MULTIMEDIA-SYSTEM-CONTROL.GSMAudioCapability.audioUnitSize
--		"audioUnitSize">--
--<OSS.FIELDNAME
--		MULTIMEDIA-SYSTEM-CONTROL.GSMAudioCapability.comfortNoise
--		"comfortNoise">--
--<OSS.FIELDNAME
--		MULTIMEDIA-SYSTEM-CONTROL.GSMAudioCapability.scrambled
--		"scrambled">--

-- ==============================================================
-- Capability exchange definitions: Data capabilities
-- ==============================================================

-- -------------------------------------------------------------- --
--
-- DataApplicationCapability   ::= SEQUENCE
-- {
--     application CHOICE
--     {
--         nonStandard NonStandardParameter,
--         t120        DataProtocolCapability,
--         dsm-cc      DataProtocolCapability,
--         userData    DataProtocolCapability,
--         t84 SEQUENCE
--         {
--             t84Protocol DataProtocolCapability,
--             t84Profile  T84Profile
--         },
--         t434    DataProtocolCapability,
--         h224    DataProtocolCapability,
--         nlpid   SEQUENCE
--         {
--             nlpidProtocol   DataProtocolCapability,
--             nlpidData       OCTET STRING
--         },
--         dsvdControl NULL,
--         h222DataPartitioning    DataProtocolCapability,
--         ...,
--         t30fax      DataProtocolCapability,
--         t140        DataProtocolCapability,
--		t38fax				SEQUENCE
--		{
--			t38faxProtocol		DataProtocolCapability,
--			t38faxRateMgmnt		T38faxRateMgmnt,
--			t38faxProfile		T38faxProfile,
--			...
--		}
--     },
--     maxBitRate  INTEGER (0..4294967295),
--     ...
-- }
--  
-- -------------------------------------------------------------- --

--<ASN1.PDU
--		MULTIMEDIA-SYSTEM-CONTROL.DataApplicationCapability>--
--<OSS.TYPENAME
--		MULTIMEDIA-SYSTEM-CONTROL.DataApplicationCapability
--		"EmDataApplicationCapability">--
--<OSS.ExtractType
--		MULTIMEDIA-SYSTEM-CONTROL.DataApplicationCapability.application>--
--<OSS.TYPENAME
--		MULTIMEDIA-SYSTEM-CONTROL.DataApplicationCapability.application
--		"EmApplication">--
--<OSS.FIELDNAME
--		MULTIMEDIA-SYSTEM-CONTROL.DataApplicationCapability.application
--		"application">--
--<OSS.FIELDNAME
--		MULTIMEDIA-SYSTEM-CONTROL.DataApplicationCapability.application.nonStandard
--		"nonStandard">--
--<OSS.DefineName
--		MULTIMEDIA-SYSTEM-CONTROL.DataApplicationCapability.application.nonStandard
--		"EM_Application_nonStandard">--
--<OSS.FIELDNAME
--		MULTIMEDIA-SYSTEM-CONTROL.DataApplicationCapability.application.t120
--		"t120">--
--<OSS.DefineName
--		MULTIMEDIA-SYSTEM-CONTROL.DataApplicationCapability.application.t120
--		"EM_Application_t120">--
--<OSS.FIELDNAME
--		MULTIMEDIA-SYSTEM-CONTROL.DataApplicationCapability.application.dsm-cc
--		"dsm_cc">--
--<OSS.DefineName
--		MULTIMEDIA-SYSTEM-CONTROL.DataApplicationCapability.application.dsm-cc
--		"EM_Application_dsm_cc">--
--<OSS.FIELDNAME
--		MULTIMEDIA-SYSTEM-CONTROL.DataApplicationCapability.application.userData
--		"userData">--
--<OSS.DefineName
--		MULTIMEDIA-SYSTEM-CONTROL.DataApplicationCapability.application.userData
--		"EM_Application_userData">--
--<OSS.InlineType
--		MULTIMEDIA-SYSTEM-CONTROL.DataApplicationCapability.application.t84>--
--<OSS.TYPENAME
--		MULTIMEDIA-SYSTEM-CONTROL.DataApplicationCapability.application.t84
--		"EmT84">--
--<OSS.FIELDNAME
--		MULTIMEDIA-SYSTEM-CONTROL.DataApplicationCapability.application.t84
--		"t84">--
--<OSS.DefineName
--		MULTIMEDIA-SYSTEM-CONTROL.DataApplicationCapability.application.t84
--		"EM_Application_t84">--
--<OSS.FIELDNAME
--		MULTIMEDIA-SYSTEM-CONTROL.DataApplicationCapability.application.t84.t84Protocol
--		"t84Protocol">--
--<OSS.FIELDNAME
--		MULTIMEDIA-SYSTEM-CONTROL.DataApplicationCapability.application.t84.t84Profile
--		"t84Profile">--
--<OSS.FIELDNAME
--		MULTIMEDIA-SYSTEM-CONTROL.DataApplicationCapability.application.t434
--		"t434">--
--<OSS.DefineName
--		MULTIMEDIA-SYSTEM-CONTROL.DataApplicationCapability.application.t434
--		"EM_Application_t434">--
--<OSS.FIELDNAME
--		MULTIMEDIA-SYSTEM-CONTROL.DataApplicationCapability.application.h224
--		"h224">--
--<OSS.DefineName
--		MULTIMEDIA-SYSTEM-CONTROL.DataApplicationCapability.application.h224
--		"EM_Application_h224">--
--<OSS.InlineType
--		MULTIMEDIA-SYSTEM-CONTROL.DataApplicationCapability.application.nlpid>--
--<OSS.TYPENAME
--		MULTIMEDIA-SYSTEM-CONTROL.DataApplicationCapability.application.nlpid
--		"EmNlpid">--
--<OSS.FIELDNAME
--		MULTIMEDIA-SYSTEM-CONTROL.DataApplicationCapability.application.nlpid
--		"nlpid">--
--<OSS.DefineName
--		MULTIMEDIA-SYSTEM-CONTROL.DataApplicationCapability.application.nlpid
--		"EM_Application_nlpid">--
--<OSS.FIELDNAME
--		MULTIMEDIA-SYSTEM-CONTROL.DataApplicationCapability.application.nlpid.nlpidProtocol
--		"nlpidProtocol">--
--<OSS.FIELDNAME
--		MULTIMEDIA-SYSTEM-CONTROL.DataApplicationCapability.application.nlpid.nlpidData
--		"nlpidData">--
--<OSS.FIELDNAME
--		MULTIMEDIA-SYSTEM-CONTROL.DataApplicationCapability.application.dsvdControl
--		"dsvdControl">--
--<OSS.DefineName
--		MULTIMEDIA-SYSTEM-CONTROL.DataApplicationCapability.application.dsvdControl
--		"EM_Application_dsvdControl">--
--<OSS.FIELDNAME
--		MULTIMEDIA-SYSTEM-CONTROL.DataApplicationCapability.application.h222DataPartitioning
--		"h222DataPartitioning">--
--<OSS.DefineName
--		MULTIMEDIA-SYSTEM-CONTROL.DataApplicationCapability.application.h222DataPartitioning
--		"EM_Application_h222DataPartitioning">--
--<OSS.FIELDNAME
--		MULTIMEDIA-SYSTEM-CONTROL.DataApplicationCapability.application.t30fax
--		"t30fax">--
--<OSS.DefineName
--		MULTIMEDIA-SYSTEM-CONTROL.DataApplicationCapability.application.t30fax
--		"EM_Application_t30fax">--
--<OSS.FIELDNAME
--		MULTIMEDIA-SYSTEM-CONTROL.DataApplicationCapability.application.t140
--		"t140">--
--<OSS.DefineName
--		MULTIMEDIA-SYSTEM-CONTROL.DataApplicationCapability.application.t140
--		"EM_Application_t140">--
--<OSS.InlineType
--		MULTIMEDIA-SYSTEM-CONTROL.DataApplicationCapability.application.t38fax>--
--<OSS.TYPENAME
--		MULTIMEDIA-SYSTEM-CONTROL.DataApplicationCapability.application.t38fax
--		"EmT38fax">--
--<OSS.FIELDNAME
--		MULTIMEDIA-SYSTEM-CONTROL.DataApplicationCapability.application.t38fax
--		"t38fax">--
--<OSS.DefineName
--		MULTIMEDIA-SYSTEM-CONTROL.DataApplicationCapability.application.t38fax
--		"EM_Application_t38fax">--
--<OSS.FIELDNAME
--		MULTIMEDIA-SYSTEM-CONTROL.DataApplicationCapability.maxBitRate
--		"maxBitRate">--

-- -------------------------------------------------------------- --
--
-- DataProtocolCapability  ::= CHOICE
-- {
--     nonStandard             NonStandardParameter,
--     v14buffered             NULL,
--     v42lapm                 NULL,
--     hdlcFrameTunnelling     NULL,
--     h310SeparateVCStack     NULL,
--     h310SingleVCStack       NULL,
--     transparent             NULL,
--     ...,
--     segmentationAndReassembly   NULL,
--     hdlcFrameTunnelingwSAR  NULL,
--     v120                    NULL,
--     separateLANStack        NULL
--     v76wCompression CHOICE
--     {
--         transmitCompression             CompressionType,
--         receiveCompression              CompressionType,
--         transmitAndReceiveCompression   CompressionType,
--         ...
--     },
--	udp	 SEQUENCE
-- 	{
--			t38UDPFEC			NULL OPTIONAL,
--			t38UDPRedundancy		NULL  OPTIONAL
--	}	(WITH COMPONENTS {t38UDPFEC, t38UDPRedundancy}  |
--		 WITH COMPONENTS {t38UDPRedundancy} ),
--	tcp							NULL
-- }
--  
-- -------------------------------------------------------------- --

--<ASN1.PDU
--		MULTIMEDIA-SYSTEM-CONTROL.DataProtocolCapability>--
--<OSS.TYPENAME
--		MULTIMEDIA-SYSTEM-CONTROL.DataProtocolCapability
--		"EmDataProtocolCapability">--
--<OSS.FIELDNAME
--		MULTIMEDIA-SYSTEM-CONTROL.DataProtocolCapability.nonStandard
--		"nonStandard">--
--<OSS.DefineName
--		MULTIMEDIA-SYSTEM-CONTROL.DataProtocolCapability.nonStandard
--		"EM_DataProtocolCapability_nonStandard">--
--<OSS.FIELDNAME
--		MULTIMEDIA-SYSTEM-CONTROL.DataProtocolCapability.v14buffered
--		"v14buffered">--
--<OSS.DefineName
--		MULTIMEDIA-SYSTEM-CONTROL.DataProtocolCapability.v14buffered
--		"EM_v14buffered">--
--<OSS.FIELDNAME
--		MULTIMEDIA-SYSTEM-CONTROL.DataProtocolCapability.v42lapm
--		"v42lapm">--
--<OSS.DefineName
--		MULTIMEDIA-SYSTEM-CONTROL.DataProtocolCapability.v42lapm
--		"EM_v42lapm">--
--<OSS.FIELDNAME
--		MULTIMEDIA-SYSTEM-CONTROL.DataProtocolCapability.hdlcFrameTunnelling
--		"hdlcFrameTunnelling">--
--<OSS.DefineName
--		MULTIMEDIA-SYSTEM-CONTROL.DataProtocolCapability.hdlcFrameTunnelling
--		"EM_hdlcFrameTunnelling">--
--<OSS.FIELDNAME
--		MULTIMEDIA-SYSTEM-CONTROL.DataProtocolCapability.h310SeparateVCStack
--		"h310SeparateVCStack">--
--<OSS.DefineName
--		MULTIMEDIA-SYSTEM-CONTROL.DataProtocolCapability.h310SeparateVCStack
--		"EM_h310SeparateVCStack">--
--<OSS.FIELDNAME
--		MULTIMEDIA-SYSTEM-CONTROL.DataProtocolCapability.h310SingleVCStack
--		"h310SingleVCStack">--
--<OSS.DefineName
--		MULTIMEDIA-SYSTEM-CONTROL.DataProtocolCapability.h310SingleVCStack
--		"EM_h310SingleVCStack">--
--<OSS.FIELDNAME
--		MULTIMEDIA-SYSTEM-CONTROL.DataProtocolCapability.transparent
--		"transparent">--
--<OSS.DefineName
--		MULTIMEDIA-SYSTEM-CONTROL.DataProtocolCapability.transparent
--		"EM_transparent">--
--<OSS.FIELDNAME
--		MULTIMEDIA-SYSTEM-CONTROL.DataProtocolCapability.segmentationAndReassembly
--		"segmentationAndReassembly">--
--<OSS.DefineName
--		MULTIMEDIA-SYSTEM-CONTROL.DataProtocolCapability.segmentationAndReassembly
--		"EM_segmentationAndReassembly">--
--<OSS.FIELDNAME
--		MULTIMEDIA-SYSTEM-CONTROL.DataProtocolCapability.hdlcFrameTunnelingwSAR
--		"hdlcFrameTunnelingwSAR">--
--<OSS.DefineName
--		MULTIMEDIA-SYSTEM-CONTROL.DataProtocolCapability.hdlcFrameTunnelingwSAR
--		"EM_hdlcFrameTunnelingwSAR">--
--<OSS.FIELDNAME
--		MULTIMEDIA-SYSTEM-CONTROL.DataProtocolCapability.v120
--		"v120">--
--<OSS.DefineName
--		MULTIMEDIA-SYSTEM-CONTROL.DataProtocolCapability.v120
--		"EM_v120">--
--<OSS.FIELDNAME
--		MULTIMEDIA-SYSTEM-CONTROL.DataProtocolCapability.separateLANStack
--		"separateLANStack">--
--<OSS.DefineName
--		MULTIMEDIA-SYSTEM-CONTROL.DataProtocolCapability.separateLANStack
--		"EM_separateLANStack">--
--<OSS.ExtractType
--		MULTIMEDIA-SYSTEM-CONTROL.DataProtocolCapability.v76wCompression>--
--<OSS.TYPENAME
--		MULTIMEDIA-SYSTEM-CONTROL.DataProtocolCapability.v76wCompression
--		"EmV76wCompression">--
--<OSS.FIELDNAME
--		MULTIMEDIA-SYSTEM-CONTROL.DataProtocolCapability.v76wCompression
--		"v76wCompression">--
--<OSS.DefineName
--		MULTIMEDIA-SYSTEM-CONTROL.DataProtocolCapability.v76wCompression
--		"EM_v76wCompression">--
--<OSS.FIELDNAME
--      MULTIMEDIA-SYSTEM-CONTROL.DataProtocolCapability.v76wCompression.transmitCompression
--      "transmitCompression">--
--<OSS.DefineName
--      MULTIMEDIA-SYSTEM-CONTROL.DataProtocolCapability.v76wCompression.transmitCompression
--      "EM_transmitCompression">--
--<OSS.FIELDNAME
--      MULTIMEDIA-SYSTEM-CONTROL.DataProtocolCapability.v76wCompression.receiveCompression
--      "receiveCompression">--
--<OSS.DefineName
--      MULTIMEDIA-SYSTEM-CONTROL.DataProtocolCapability.v76wCompression.receiveCompression
--      "EM_receiveCompression">--
--<OSS.FIELDNAME
--      MULTIMEDIA-SYSTEM-CONTROL.DataProtocolCapability.v76wCompression.transmitAndReceiveCompression
--      "transmitAndReceiveCompression">--
--<OSS.DefineName
--      MULTIMEDIA-SYSTEM-CONTROL.DataProtocolCapability.v76wCompression.transmitAndReceiveCompression
--      "EM_transmitAndReceiveCompression">--

--<OSS.ExtractType
--		MULTIMEDIA-SYSTEM-CONTROL.DataProtocolCapability.udp>--
--<OSS.TYPENAME
--		MULTIMEDIA-SYSTEM-CONTROL.DataProtocolCapability.udp
--		"EmDataProtocolCapabilityUDP">--
--<OSS.FIELDNAME
--		MULTIMEDIA-SYSTEM-CONTROL.DataProtocolCapability.udp
--		"udp">--
--<OSS.DefineName
--		MULTIMEDIA-SYSTEM-CONTROL.DataProtocolCapability.udp
--		"EM_DataProtocolCapability_udp">--
--<OSS.FIELDNAME
--      MULTIMEDIA-SYSTEM-CONTROL.DataProtocolCapability.udp.t38UDPFEC
--      "t38UDPFEC">--
--<OSS.DefineName
--      MULTIMEDIA-SYSTEM-CONTROL.DataProtocolCapability.udp.t38UDPFEC
--      "EM_t38UDPFEC">--
--<OSS.FIELDNAME
--      MULTIMEDIA-SYSTEM-CONTROL.DataProtocolCapability.udp.t38UDPRedundancy
--      "t38UDPRedundancy">--
--<OSS.DefineName
--      MULTIMEDIA-SYSTEM-CONTROL.DataProtocolCapability.udp.t38UDPRedundancy
--      "EM_t38UDPRedundancy">--

--<OSS.FIELDNAME
--		MULTIMEDIA-SYSTEM-CONTROL.DataProtocolCapability.tcp
--		"tcp">--
--<OSS.DefineName
--		MULTIMEDIA-SYSTEM-CONTROL.DataProtocolCapability.tcp
--		"EM_DataProtocolCapability_tcp">--
-- -------------------------------------------------------------- --
--
-- CompressionType ::= CHOICE
-- {
--     v42bis      V42bis,
--     ...
-- }
--  
-- -------------------------------------------------------------- --

--<ASN1.PDU
--		MULTIMEDIA-SYSTEM-CONTROL.CompressionType>--
--<OSS.TYPENAME
--		MULTIMEDIA-SYSTEM-CONTROL.CompressionType
--		"EmCompressionType">--
--<OSS.FIELDNAME
--		MULTIMEDIA-SYSTEM-CONTROL.CompressionType.v42bis
--		"v42bis">--
--<OSS.DefineName
--		MULTIMEDIA-SYSTEM-CONTROL.CompressionType.v42bis
--		"EM_v42bis">--

-- -------------------------------------------------------------- --
--
-- V42bis ::= SEQUENCE
-- {
--     numberOfCodewords   INTEGER (1..65536),
--     maximumStringLength INTEGER (1..256),
--     ...
-- }
--
-- -------------------------------------------------------------- --

--<ASN1.PDU
--		MULTIMEDIA-SYSTEM-CONTROL.V42bis>--
--<OSS.TYPENAME
--		MULTIMEDIA-SYSTEM-CONTROL.V42bis
--		"EmV42bis">--
--<OSS.FIELDNAME
--		MULTIMEDIA-SYSTEM-CONTROL.V42bis.numberOfCodewords
--		"numberOfCodewords">--
--<OSS.FIELDNAME
--		MULTIMEDIA-SYSTEM-CONTROL.V42bis.maximumStringLength
--		"maximumStringLength">--

-- -------------------------------------------------------------- --
--
-- T84Profile      ::= CHOICE
-- {
--     t84Unrestricted NULL,
--     t84Restricted   SEQUENCE
--     {
--         qcif                BOOLEAN,
--         cif                 BOOLEAN,
--         ccir601Seq          BOOLEAN,
--         ccir601Prog         BOOLEAN,
--         hdtvSeq             BOOLEAN,
--         hdtvProg            BOOLEAN,
--  
--         g3FacsMH200x100     BOOLEAN,
--         g3FacsMH200x200     BOOLEAN,
--         g4FacsMMR200x100    BOOLEAN,
--         g4FacsMMR200x200    BOOLEAN,
--         jbig200x200Seq      BOOLEAN,
--         jbig200x200Prog     BOOLEAN,
--         jbig300x300Seq      BOOLEAN,
--         jbig300x300Prog     BOOLEAN,
--  
--         digPhotoLow         BOOLEAN,
--         digPhotoMedSeq      BOOLEAN,
--         digPhotoMedProg     BOOLEAN,
--         digPhotoHighSeq     BOOLEAN,
--         digPhotoHighProg    BOOLEAN,
--  
--         ...
--     }
-- }
--
-- -------------------------------------------------------------- --

--<ASN1.PDU
--		MULTIMEDIA-SYSTEM-CONTROL.T84Profile>--
--<OSS.TYPENAME
--		MULTIMEDIA-SYSTEM-CONTROL.T84Profile
--		"EmT84Profile">--
--<OSS.FIELDNAME
--		MULTIMEDIA-SYSTEM-CONTROL.T84Profile.t84Unrestricted
--		"t84Unrestricted">--
--<OSS.DefineName
--		MULTIMEDIA-SYSTEM-CONTROL.T84Profile.t84Unrestricted
--		"EM_t84Unrestricted">--
--<OSS.FIELDNAME
--		MULTIMEDIA-SYSTEM-CONTROL.T84Profile.t84Restricted
--		"t84Restricted">--
--<OSS.DefineName
--		MULTIMEDIA-SYSTEM-CONTROL.T84Profile.t84Restricted
--		"EM_t84Restricted">--
--<OSS.InlineType
--		MULTIMEDIA-SYSTEM-CONTROL.T84Profile.t84Restricted>--
--<OSS.TYPENAME
--		MULTIMEDIA-SYSTEM-CONTROL.T84Profile.t84Restricted
--		"EmT84Restricted">--
--<OSS.FIELDNAME
--      MULTIMEDIA-SYSTEM-CONTROL.T84Profile.t84Restricted.qcif
--      "qcif">--
--<OSS.FIELDNAME
--      MULTIMEDIA-SYSTEM-CONTROL.T84Profile.t84Restricted.cif
--      "cif">--
--<OSS.FIELDNAME
--      MULTIMEDIA-SYSTEM-CONTROL.T84Profile.t84Restricted.ccir601Seq
--      "ccir601Seq">--
--<OSS.FIELDNAME
--      MULTIMEDIA-SYSTEM-CONTROL.T84Profile.t84Restricted.ccir601Prog
--      "ccir601Prog">--
--<OSS.FIELDNAME
--      MULTIMEDIA-SYSTEM-CONTROL.T84Profile.t84Restricted.hdtvSeq
--      "hdtvSeq">--
--<OSS.FIELDNAME
--      MULTIMEDIA-SYSTEM-CONTROL.T84Profile.t84Restricted.hdtvProg
--      "hdtvProg">--
--<OSS.FIELDNAME
--      MULTIMEDIA-SYSTEM-CONTROL.T84Profile.t84Restricted.g3FacsMH200x100
--      "g3FacsMH200x100">--
--<OSS.FIELDNAME
--      MULTIMEDIA-SYSTEM-CONTROL.T84Profile.t84Restricted.g3FacsMH200x200
--      "g3FacsMH200x200">--
--<OSS.FIELDNAME
--      MULTIMEDIA-SYSTEM-CONTROL.T84Profile.t84Restricted.g4FacsMMR200x100
--      "g4FacsMMR200x100">--
--<OSS.FIELDNAME
--      MULTIMEDIA-SYSTEM-CONTROL.T84Profile.t84Restricted.g4FacsMMR200x200
--      "g4FacsMMR200x200">--
--<OSS.FIELDNAME
--      MULTIMEDIA-SYSTEM-CONTROL.T84Profile.t84Restricted.jbig200x200Seq
--      "jbig200x200Seq">--
--<OSS.FIELDNAME
--      MULTIMEDIA-SYSTEM-CONTROL.T84Profile.t84Restricted.jbig200x200Prog
--      "jbig200x200Prog">--
--<OSS.FIELDNAME
--      MULTIMEDIA-SYSTEM-CONTROL.T84Profile.t84Restricted.jbig300x300Seq
--      "jbig300x300Seq">--
--<OSS.FIELDNAME
--      MULTIMEDIA-SYSTEM-CONTROL.T84Profile.t84Restricted.jbig300x300Prog
--      "jbig300x300Prog">--
--<OSS.FIELDNAME
--      MULTIMEDIA-SYSTEM-CONTROL.T84Profile.t84Restricted.digPhotoLow
--      "digPhotoLow">--
--<OSS.FIELDNAME
--      MULTIMEDIA-SYSTEM-CONTROL.T84Profile.t84Restricted.digPhotoMedSeq
--      "digPhotoMedSeq">--
--<OSS.FIELDNAME
--      MULTIMEDIA-SYSTEM-CONTROL.T84Profile.t84Restricted.digPhotoMedProg
--      "digPhotoMedProg">--
--<OSS.FIELDNAME
--      MULTIMEDIA-SYSTEM-CONTROL.T84Profile.t84Restricted.digPhotoHighSeq
--      "digPhotoHighSeq">--
--<OSS.FIELDNAME
--      MULTIMEDIA-SYSTEM-CONTROL.T84Profile.t84Restricted.digPhotoHighProg
--      "digPhotoHighProg">--

-- -------------------------------------------------------------- --
--T38fax								::=	SEQUENCE
--{
--	t38faxProtocol		DataProtocolCapability,
--	t38faxRateMgmnt		T38faxRateMgmnt,
--	t38faxProfile		T38faxProfile,
--	...
--}
--
-- -------------------------------------------------------------- --

--<ASN1.PDU
--		MULTIMEDIA-SYSTEM-CONTROL.T38fax>--
--<OSS.TYPENAME
--		MULTIMEDIA-SYSTEM-CONTROL.T38fax
--		"EmT38fax">--
--<OSS.FIELDNAME
--		MULTIMEDIA-SYSTEM-CONTROL.T38fax.t38faxProtocol
--		"t38faxProtocol">--
--<OSS.DefineName
--		MULTIMEDIA-SYSTEM-CONTROL.T38fax.t38faxProtocol
--		"EM_T38fax_t38faxProtocol">--
--<OSS.FIELDNAME
--		MULTIMEDIA-SYSTEM-CONTROL.T38fax.t38faxRateMgmnt
--		"t38faxRateMgmnt">--
--<OSS.DefineName
--		MULTIMEDIA-SYSTEM-CONTROL.T38fax.t38faxRateMgmnt
--		"EM_T38fax_t38faxRateMgmnt">--
--<OSS.FIELDNAME
--		MULTIMEDIA-SYSTEM-CONTROL.T38fax.t38faxProfile
--		"t38faxProfile">--
--<OSS.DefineName
--		MULTIMEDIA-SYSTEM-CONTROL.T38fax.t38faxProfile
--		"EM_T38fax_t38faxProfile">--

-- -------------------------------------------------------------- --
--T38faxProfile						::= SEQUENCE
--{
--	fillBitRemoval					NULL OPTIONAL,
--	transcodingJBIG				NULL OPTIONAL,
--	transcodingMMR			NULL OPTIONAL,
--	t38faxMaxBuffer			INTEGER OPTIONAL,
--	t38faxMaxDatagram			INTEGER OPTIONAL,
--	version						INTEGER   (0..255),
--
--	...
--}
-- -------------------------------------------------------------- --

--<ASN1.PDU
--		MULTIMEDIA-SYSTEM-CONTROL.T38faxProfile>--
--<OSS.TYPENAME
--		MULTIMEDIA-SYSTEM-CONTROL.T38faxProfile
--		"EmT38faxProfile">--
--<OSS.FIELDNAME
--		MULTIMEDIA-SYSTEM-CONTROL.T38faxProfile.fillBitRemoval
--		"fillBitRemoval">--
--<OSS.DefineName
--		MULTIMEDIA-SYSTEM-CONTROL.T38faxProfile.fillBitRemoval
--		"EM_T38faxProfile_fillBitRemoval">--
--<OSS.FIELDNAME
--		MULTIMEDIA-SYSTEM-CONTROL.T38faxProfile.transcodingJBIG
--		"transcodingJBIG">--
--<OSS.DefineName
--		MULTIMEDIA-SYSTEM-CONTROL.T38faxProfile.transcodingJBIG
--		"EM_T38faxProfile_transcodingJBIG">--
--<OSS.FIELDNAME
--		MULTIMEDIA-SYSTEM-CONTROL.T38faxProfile.transcodingMMR
--		"transcodingMMR">--
--<OSS.DefineName
--		MULTIMEDIA-SYSTEM-CONTROL.T38faxProfile.transcodingMMR
--		"EM_T38faxProfile_transcodingMMR">--
--<OSS.FIELDNAME
--		MULTIMEDIA-SYSTEM-CONTROL.T38faxProfile.t38faxMaxBuffer
--		"t38faxMaxBuffer">--
--<OSS.DefineName
--		MULTIMEDIA-SYSTEM-CONTROL.T38faxProfile.t38faxMaxBuffer
--		"EM_T38faxProfile_t38faxMaxBuffer">--
--<OSS.FIELDNAME
--		MULTIMEDIA-SYSTEM-CONTROL.T38faxProfile.t38faxMaxDatagram
--		"t38faxMaxDatagram">--
--<OSS.DefineName
--		MULTIMEDIA-SYSTEM-CONTROL.T38faxProfile.t38faxMaxDatagram
--		"EM_T38faxProfile_t38faxMaxDatagram">--
--<OSS.FIELDNAME
--		MULTIMEDIA-SYSTEM-CONTROL.T38faxProfile.version
--		"version">--
--<OSS.DefineName
--		MULTIMEDIA-SYSTEM-CONTROL.T38faxProfile.version
--		"EM_T38faxProfile_version">--


-- -------------------------------------------------------------- --
--T38faxRateMgmnt					::= CHOICE
--{
--	localTCF						NULL,
--	transferredTCF				NULL
--}
-- -------------------------------------------------------------- --

--<ASN1.PDU
--		MULTIMEDIA-SYSTEM-CONTROL.T38faxRateMgmnt>--
--<OSS.TYPENAME
--		MULTIMEDIA-SYSTEM-CONTROL.T38faxRateMgmnt
--		"EmT38faxRateMgmnt">--
--<OSS.FIELDNAME
--		MULTIMEDIA-SYSTEM-CONTROL.T38faxRateMgmnt.localTCF
--		"localTCF">--
--<OSS.DefineName
--		MULTIMEDIA-SYSTEM-CONTROL.T38faxRateMgmnt.localTCF
--		"EM_T38faxRateMgmnt_localTCF">--
--<OSS.FIELDNAME
--		MULTIMEDIA-SYSTEM-CONTROL.T38faxRateMgmnt.transferredTCF
--		"transferredTCF">--
--<OSS.DefineName
--		MULTIMEDIA-SYSTEM-CONTROL.T38faxRateMgmnt.transferredTCF
--		"EM_T38faxRateMgmnt_transferredTCF">--
-- ==============================================================
-- Encryption Capability Definitions:
-- ==============================================================

-- -------------------------------------------------------------- --
--
-- EncryptionAuthenticationAndIntegrity ::= SEQUENCE
-- {
--     encryptionCapability        EncryptionCapability OPTIONAL,
--     authenticationCapability    AuthenticationCapability OPTIONAL,
--     integrityCapability         IntegrityCapability OPTIONAL,
--     ...
-- }
--
-- -------------------------------------------------------------- --

--<ASN1.PDU
--		MULTIMEDIA-SYSTEM-CONTROL.EncryptionAuthenticationAndIntegrity>--
--<OSS.TYPENAME
--		MULTIMEDIA-SYSTEM-CONTROL.EncryptionAuthenticationAndIntegrity
--		"EmEncryptionAuthenticationAndIntegrity">--
--<OSS.FIELDNAME
--		MULTIMEDIA-SYSTEM-CONTROL.EncryptionAuthenticationAndIntegrity.encryptionCapability
--		"encryptionCapability">--
--<OSS.DefineName
--		MULTIMEDIA-SYSTEM-CONTROL.EncryptionAuthenticationAndIntegrity.encryptionCapability
--		"EM_encryptionCapability">--
--<OSS.FIELDNAME
--		MULTIMEDIA-SYSTEM-CONTROL.EncryptionAuthenticationAndIntegrity.authenticationCapability
--		"authenticationCapability">--
--<OSS.DefineName
--		MULTIMEDIA-SYSTEM-CONTROL.EncryptionAuthenticationAndIntegrity.authenticationCapability
--		"EM_authenticationCapability">--
--<OSS.FIELDNAME
--		MULTIMEDIA-SYSTEM-CONTROL.EncryptionAuthenticationAndIntegrity.integrityCapability
--		"integrityCapability">--
--<OSS.DefineName
--		MULTIMEDIA-SYSTEM-CONTROL.EncryptionAuthenticationAndIntegrity.integrityCapability
--		"EM_integrityCapability">--

-- -------------------------------------------------------------- --
--  
-- EncryptionCapability ::= SeqOf256MediaEncryptionAlgorithm
--
-- -------------------------------------------------------------- --

--<ASN1.PDU
--		MULTIMEDIA-SYSTEM-CONTROL.EncryptionCapability>--
--<OSS.FIELDNAME
--		MULTIMEDIA-SYSTEM-CONTROL.EncryptionCapability
--		"EmEncryptionCapability">--

-- -------------------------------------------------------------- --
--  
-- MediaEncryptionAlgorithm ::= CHOICE
-- {
--     nonStandard             NonStandardParameter,
--     algorithm               OBJECT IDENTIFIER,
--     ...
-- }
--
-- -------------------------------------------------------------- --

--<ASN1.PDU
--		MULTIMEDIA-SYSTEM-CONTROL.MediaEncryptionAlgorithm>--
--<OSS.TYPENAME
--		MULTIMEDIA-SYSTEM-CONTROL.MediaEncryptionAlgorithm
--		"EmMediaEncryptionAlgorithm">--
--<OSS.FIELDNAME
--		MULTIMEDIA-SYSTEM-CONTROL.MediaEncryptionAlgorithm.nonStandard
--		"nonStandard">--
--<OSS.DefineName
--		MULTIMEDIA-SYSTEM-CONTROL.MediaEncryptionAlgorithm.nonStandard
--		"EM_MediaEncryptionAlgorithm_nonStandard">--
--<OSS.FIELDNAME
--		MULTIMEDIA-SYSTEM-CONTROL.MediaEncryptionAlgorithm.algorithm
--		"algorithm">--
--<OSS.DefineName
--		MULTIMEDIA-SYSTEM-CONTROL.MediaEncryptionAlgorithm.algorithm
--		"EM_algorithm">--

-- -------------------------------------------------------------- --
--  
-- AuthenticationCapability ::= SEQUENCE
-- {
--     nonStandard             NonStandardParameter OPTIONAL,
--     ...
-- }
--
-- -------------------------------------------------------------- --

--<ASN1.PDU
--		MULTIMEDIA-SYSTEM-CONTROL.AuthenticationCapability>--
--<OSS.TYPENAME
--		MULTIMEDIA-SYSTEM-CONTROL.AuthenticationCapability
--		"EmAuthenticationCapability">--
--<OSS.FIELDNAME
--		MULTIMEDIA-SYSTEM-CONTROL.AuthenticationCapability.nonStandard
--		"nonStandard">--
--<OSS.DefineName
--		MULTIMEDIA-SYSTEM-CONTROL.AuthenticationCapability.nonStandard
--		"EM_AuthenticationCapability_nonStandard">--

-- -------------------------------------------------------------- --
--  
-- IntegrityCapability ::= SEQUENCE
-- {
--     nonStandard             NonStandardParameter OPTIONAL,
--     ...
-- }
--
-- -------------------------------------------------------------- --

--<ASN1.PDU
--		MULTIMEDIA-SYSTEM-CONTROL.IntegrityCapability>--
--<OSS.TYPENAME
--		MULTIMEDIA-SYSTEM-CONTROL.IntegrityCapability
--		"EmIntegrityCapability">--
--<OSS.FIELDNAME
--		MULTIMEDIA-SYSTEM-CONTROL.IntegrityCapability.nonStandard
--		"nonStandard">--
--<OSS.DefineName
--		MULTIMEDIA-SYSTEM-CONTROL.IntegrityCapability.nonStandard
--		"EM_IntegrityCapability_nonStandard">--

-- ==============================================================
-- Capability Exchange Definitions: UserInput
-- ==============================================================

-- -------------------------------------------------------------- --
--
-- UserInputCapability ::= CHOICE
-- {
--     nonStandard     SeqOf16NonStandardParameter,
--     basicString     NULL,
--     iA5String       NULL,
--     generalString   NULL,
--     dtmf            NULL,
--     hookflash       NULL,
--     ...
-- }
--
-- -------------------------------------------------------------- --

--<ASN1.PDU
--		MULTIMEDIA-SYSTEM-CONTROL.UserInputCapability>--
--<OSS.TYPENAME
--		MULTIMEDIA-SYSTEM-CONTROL.UserInputCapability
--		"EmUserInputCapability">--
--<OSS.FIELDNAME
--		MULTIMEDIA-SYSTEM-CONTROL.UserInputCapability.nonStandard
--		"nonStandard">--
--<OSS.DefineName
--		MULTIMEDIA-SYSTEM-CONTROL.UserInputCapability.nonStandard
--		"EM_UserInputCapability_nonStandard">--
--<OSS.FIELDNAME
--		MULTIMEDIA-SYSTEM-CONTROL.UserInputCapability.basicString
--		"basicString">--
--<OSS.DefineName
--		MULTIMEDIA-SYSTEM-CONTROL.UserInputCapability.basicString
--		"EM_UserInputCapability_basicString">--
--<OSS.FIELDNAME
--		MULTIMEDIA-SYSTEM-CONTROL.UserInputCapability.iA5String
--		"iA5String">--
--<OSS.DefineName
--		MULTIMEDIA-SYSTEM-CONTROL.UserInputCapability.iA5String
--		"EM_UserInputCapability_iA5String">--
--<OSS.FIELDNAME
--		MULTIMEDIA-SYSTEM-CONTROL.UserInputCapability.generalString
--		"generalString">--
--<OSS.DefineName
--		MULTIMEDIA-SYSTEM-CONTROL.UserInputCapability.generalString
--		"EM_UserInputCapability_generalString">--
--<OSS.FIELDNAME
--		MULTIMEDIA-SYSTEM-CONTROL.UserInputCapability.dtmf
--		"dtmf">--
--<OSS.DefineName
--		MULTIMEDIA-SYSTEM-CONTROL.UserInputCapability.dtmf
--		"EM_dtmf">--
--<OSS.FIELDNAME
--		MULTIMEDIA-SYSTEM-CONTROL.UserInputCapability.hookflash
--		"hookflash">--
--<OSS.DefineName
--		MULTIMEDIA-SYSTEM-CONTROL.UserInputCapability.hookflash
--		"EM_hookflash">--

-- ==============================================================
-- Capability Exchange Definitions: Conference
-- ==============================================================

-- -------------------------------------------------------------- --
--
-- ConferenceCapability    ::= SEQUENCE
-- {
--     nonStandardData         SEQUENCE OF NonStandardParameter OPTIONAL,
--     chairControlCapability  BOOLEAN,
--     ...
-- 	   videoIndicateMixingCapability	BOOLEAN
-- }
--
-- -------------------------------------------------------------- --

--<ASN1.PDU
--		MULTIMEDIA-SYSTEM-CONTROL.ConferenceCapability>--
--<OSS.TYPENAME
--		MULTIMEDIA-SYSTEM-CONTROL.ConferenceCapability
--		"EmConferenceCapability">--
--<OSS.FIELDNAME
--		MULTIMEDIA-SYSTEM-CONTROL.ConferenceCapability.nonStandardData
--		"nonStandardData">--
--<OSS.DefineName
--		MULTIMEDIA-SYSTEM-CONTROL.ConferenceCapability.nonStandardData
--		"EM_ConferenceCapability_nonStandardData">--
--<OSS.FIELDNAME
--		MULTIMEDIA-SYSTEM-CONTROL.ConferenceCapability.chairControlCapability
--		"chairControlCapability">--
--<OSS.FIELDNAME
--		MULTIMEDIA-SYSTEM-CONTROL.ConferenceCapability.videoIndicateMixingCapability
--		"videoIndicateMixingCapability">--
--<OSS.DefineName
--		MULTIMEDIA-SYSTEM-CONTROL.ConferenceCapability.videoIndicateMixingCapability
--		"EM_videoIndicateMixingCapability">--

-- ==============================================================
-- Logical channel signalling definitions
-- ==============================================================

-- -------------------------------------------------------------- --
--
-- OpenLogicalChannel  ::= SEQUENCE
-- {
--     forwardLogicalChannelNumber     LogicalChannelNumber,
--  
--     forwardLogicalChannelParameters SEQUENCE
--     {
--         portNumber  INTEGER (0..65535)  OPTIONAL,
--         dataType    DataType,
--         multiplexParameters CHOICE
--         {
--             h222LogicalChannelParameters    H222LogicalChannelParameters,
--             h223LogicalChannelParameters    H223LogicalChannelParameters,
--             v76LogicalChannelParameters     V76LogicalChannelParameters,
--             ...,
--             h2250LogicalChannelParameters   H2250LogicalChannelParameters,
--             none                            NULL
--         },
--         ...,
--         forwardLogicalChannelDependency LogicalChannelNumber OPTIONAL,
--
--         replacementFor                  LogicalChannelNumber OPTIONAL
--     },
--  
--     reverseLogicalChannelParameters SEQUENCE
--     {
--         dataType    DataType,
--         multiplexParameters CHOICE
--         {
--             h223LogicalChannelParameters    H223LogicalChannelParameters,
--             v76LogicalChannelParameters     V76LogicalChannelParameters,
--             ...,
--             h2250LogicalChannelParameters   H2250LogicalChannelParameters,
--  
--         }  OPTIONAL,
--         ...,
--         reverseLogicalChannelDependency LogicalChannelNumber OPTIONAL,
--
--         replacementFor                  LogicalChannelNumber OPTIONAL
--
--     }  OPTIONAL,
--     ...,
--     separateStack   NetworkAccessParameters  OPTIONAL
--
--     encryptionSync  EncryptionSync OPTIONAL
--
-- }
--
-- -------------------------------------------------------------- --

--<ASN1.PDU 
--		MULTIMEDIA-SYSTEM-CONTROL.OpenLogicalChannel>--
--<OSS.TYPENAME
--		MULTIMEDIA-SYSTEM-CONTROL.OpenLogicalChannel
--		"EmOpenLogicalChannel">--

--<OSS.FIELDNAME
--		MULTIMEDIA-SYSTEM-CONTROL.OpenLogicalChannel.forwardLogicalChannelNumber
--		"forwardLogicalChannelNumber">--

--<OSS.ExtractType
--		MULTIMEDIA-SYSTEM-CONTROL.OpenLogicalChannel.forwardLogicalChannelParameters>--
--<OSS.TYPENAME
--		MULTIMEDIA-SYSTEM-CONTROL.OpenLogicalChannel.forwardLogicalChannelParameters
--		"EmOLCForwardLogicalChannelParameters">--
--<OSS.FIELDNAME
--		MULTIMEDIA-SYSTEM-CONTROL.OpenLogicalChannel.forwardLogicalChannelParameters
--		"forwardLogicalChannelParameters">--
--<OSS.FIELDNAME
--		MULTIMEDIA-SYSTEM-CONTROL.OpenLogicalChannel.forwardLogicalChannelParameters.portNumber
--		"portNumber">--
--<OSS.DefineName
--		MULTIMEDIA-SYSTEM-CONTROL.OpenLogicalChannel.forwardLogicalChannelParameters.portNumber
--		"EM_OLCFwdLCP_portNumber">--
--<OSS.FIELDNAME
--		MULTIMEDIA-SYSTEM-CONTROL.OpenLogicalChannel.forwardLogicalChannelParameters.dataType
--		"dataType">--

--<OSS.ExtractType
--		MULTIMEDIA-SYSTEM-CONTROL.OpenLogicalChannel.forwardLogicalChannelParameters.multiplexParameters>--
--<OSS.TYPENAME
--		MULTIMEDIA-SYSTEM-CONTROL.OpenLogicalChannel.forwardLogicalChannelParameters.multiplexParameters
--		"EmOLCFwdLCPMultiplexParameters">--
--<OSS.FIELDNAME
--		MULTIMEDIA-SYSTEM-CONTROL.OpenLogicalChannel.forwardLogicalChannelParameters.multiplexParameters
--		"multiplexParameters">--

--<ASN1.Remove
--		MULTIMEDIA-SYSTEM-CONTROL.OpenLogicalChannel.forwardLogicalChannelParameters.multiplexParameters.h222LogicalChannelParameters>--
--<ASN1.Remove
--		MULTIMEDIA-SYSTEM-CONTROL.OpenLogicalChannel.forwardLogicalChannelParameters.multiplexParameters.h223LogicalChannelParameters>--
--<ASN1.Remove
--		MULTIMEDIA-SYSTEM-CONTROL.OpenLogicalChannel.forwardLogicalChannelParameters.multiplexParameters.v76LogicalChannelParameters>--

--<OSS.FIELDNAME
--		MULTIMEDIA-SYSTEM-CONTROL.OpenLogicalChannel.forwardLogicalChannelParameters.multiplexParameters.h2250LogicalChannelParameters
--		"h2250LogicalChannelParameters">--
--<OSS.DefineName
--		MULTIMEDIA-SYSTEM-CONTROL.OpenLogicalChannel.forwardLogicalChannelParameters.multiplexParameters.h2250LogicalChannelParameters
--		"EM_OLCFwdLCP_h2250LogicalChannelParameters">--
--<OSS.FIELDNAME
--		MULTIMEDIA-SYSTEM-CONTROL.OpenLogicalChannel.forwardLogicalChannelParameters.multiplexParameters.none
--		"none">--
--<OSS.DefineName
--		MULTIMEDIA-SYSTEM-CONTROL.OpenLogicalChannel.forwardLogicalChannelParameters.multiplexParameters.none
--		"EM_OLCFwdLCP_none">--
--<OSS.FIELDNAME
--		MULTIMEDIA-SYSTEM-CONTROL.OpenLogicalChannel.forwardLogicalChannelParameters.forwardLogicalChannelDependency
--		"forwardLogicalChannelDependency">--
--<OSS.DefineName
--		MULTIMEDIA-SYSTEM-CONTROL.OpenLogicalChannel.forwardLogicalChannelParameters.forwardLogicalChannelDependency
--		"EM_forwardLogicalChannelDependency">--
--<OSS.FIELDNAME
--		MULTIMEDIA-SYSTEM-CONTROL.OpenLogicalChannel.forwardLogicalChannelParameters.replacementFor
--		"replacementFor">--
--<OSS.DefineName
--		MULTIMEDIA-SYSTEM-CONTROL.OpenLogicalChannel.forwardLogicalChannelParameters.replacementFor
--		"EM_OLCFwdLCP_replacementFor">--

--<OSS.ExtractType
--		MULTIMEDIA-SYSTEM-CONTROL.OpenLogicalChannel.reverseLogicalChannelParameters>--
--<OSS.TYPENAME
--		MULTIMEDIA-SYSTEM-CONTROL.OpenLogicalChannel.reverseLogicalChannelParameters
--		"EmOLCReverseLogicalChannelParameters">--
--<OSS.FIELDNAME
--		MULTIMEDIA-SYSTEM-CONTROL.OpenLogicalChannel.reverseLogicalChannelParameters
--		"reverseLogicalChannelParameters">--
--<OSS.DefineName
--		MULTIMEDIA-SYSTEM-CONTROL.OpenLogicalChannel.reverseLogicalChannelParameters
--		"EM_OLC_reverseLogicalChannelParameters">--
--<OSS.FIELDNAME
--		MULTIMEDIA-SYSTEM-CONTROL.OpenLogicalChannel.reverseLogicalChannelParameters.dataType
--		"dataType">--

--<OSS.ExtractType
--		MULTIMEDIA-SYSTEM-CONTROL.OpenLogicalChannel.reverseLogicalChannelParameters.multiplexParameters>--
--<OSS.TYPENAME
--		MULTIMEDIA-SYSTEM-CONTROL.OpenLogicalChannel.reverseLogicalChannelParameters.multiplexParameters
--		"EmOLCRevLCPMultiplexParameters">--
--<OSS.FIELDNAME
--		MULTIMEDIA-SYSTEM-CONTROL.OpenLogicalChannel.reverseLogicalChannelParameters.multiplexParameters
--		"multiplexParameters">--
--<OSS.DefineName
--		MULTIMEDIA-SYSTEM-CONTROL.OpenLogicalChannel.reverseLogicalChannelParameters.multiplexParameters
--		"EM_OLCRevLCP_multiplexParameters">--

--<ASN1.Remove
--		MULTIMEDIA-SYSTEM-CONTROL.OpenLogicalChannel.reverseLogicalChannelParameters.multiplexParameters.h223LogicalChannelParameters>--
--<ASN1.Remove
--		MULTIMEDIA-SYSTEM-CONTROL.OpenLogicalChannel.reverseLogicalChannelParameters.multiplexParameters.v76LogicalChannelParameters>--

--<OSS.FIELDNAME
--		MULTIMEDIA-SYSTEM-CONTROL.OpenLogicalChannel.reverseLogicalChannelParameters.multiplexParameters.h2250LogicalChannelParameters
--		"h2250LogicalChannelParameters">--
--<OSS.DefineName
--		MULTIMEDIA-SYSTEM-CONTROL.OpenLogicalChannel.reverseLogicalChannelParameters.multiplexParameters.h2250LogicalChannelParameters
--		"EM_OLCRevLCP_h2250LogicalChannelParameters">--

--<OSS.FIELDNAME
--		MULTIMEDIA-SYSTEM-CONTROL.OpenLogicalChannel.reverseLogicalChannelParameters.reverseLogicalChannelDependency
--		"reverseLogicalChannelDependency">--
--<OSS.DefineName
--		MULTIMEDIA-SYSTEM-CONTROL.OpenLogicalChannel.reverseLogicalChannelParameters.reverseLogicalChannelDependency
--		"EM_reverseLogicalChannelDependency">--
--<OSS.FIELDNAME
--		MULTIMEDIA-SYSTEM-CONTROL.OpenLogicalChannel.reverseLogicalChannelParameters.replacementFor
--		"replacementFor">--
--<OSS.DefineName
--		MULTIMEDIA-SYSTEM-CONTROL.OpenLogicalChannel.reverseLogicalChannelParameters.replacementFor
--		"EM_OLCRevLCP_replacementFor">--

--<OSS.FIELDNAME
--		MULTIMEDIA-SYSTEM-CONTROL.OpenLogicalChannel.separateStack
--		"separateStack">--
--<OSS.DefineName
--		MULTIMEDIA-SYSTEM-CONTROL.OpenLogicalChannel.separateStack
--		"EM_OLC_separateStack">--
--<OSS.FIELDNAME
--		MULTIMEDIA-SYSTEM-CONTROL.OpenLogicalChannel.encryptionSync
--		"encryptionSync">--
--<OSS.DefineName
--		MULTIMEDIA-SYSTEM-CONTROL.OpenLogicalChannel.encryptionSync
--		"EM_OLC_encryptionSync">--

-- -------------------------------------------------------------- --
--  
-- LogicalChannelNumber    ::=INTEGER (1..65535)
--
-- -------------------------------------------------------------- --

--<OSS.TYPENAME
--		MULTIMEDIA-SYSTEM-CONTROL.LogicalChannelNumber
--		"EmLogicalChannelNumber">--

-- -------------------------------------------------------------- --
--  
-- NetworkAccessParameters ::= SEQUENCE
-- {
--     distribution    CHOICE
--     {
--         unicast     NULL,
--         multicast   NULL,
--         ...
--     }  OPTIONAL,
--  
--     networkAddress  CHOICE
--     {
--         q2931Address        Q2931Address,
--         e164Address         IA5String(SIZE(1..128)) (FROM ("0123456789#*,")),
--         localAreaAddress    TransportAddress,
--         ...
--     },
--     associateConference BOOLEAN,
--     externalReference   OCTET STRING(SIZE(1..255))  OPTIONAL,
--     ...,
--     t120SetupProcedure  CHOICE
--     {
--  
--         originateCall   NULL,
--         waitForCall     NULL,
--         issueQuery      NULL,
--         ...
--     } OPTIONAL
-- }
--
-- -------------------------------------------------------------- --

--<ASN1.PDU 
--		MULTIMEDIA-SYSTEM-CONTROL.NetworkAccessParameters>--
--<OSS.TYPENAME
--		MULTIMEDIA-SYSTEM-CONTROL.NetworkAccessParameters
--		"EmNetworkAccessParameters">--

--<OSS.ExtractType
--		MULTIMEDIA-SYSTEM-CONTROL.NetworkAccessParameters.distribution>--
--<OSS.TYPENAME
--		MULTIMEDIA-SYSTEM-CONTROL.NetworkAccessParameters.distribution
--		"EmDistribution">--
--<OSS.FIELDNAME
--		MULTIMEDIA-SYSTEM-CONTROL.NetworkAccessParameters.distribution
--		"distribution">--
--<OSS.DefineName
--		MULTIMEDIA-SYSTEM-CONTROL.NetworkAccessParameters.distribution
--		"EM_distribution">--
--<OSS.FIELDNAME
--		MULTIMEDIA-SYSTEM-CONTROL.NetworkAccessParameters.distribution.unicast
--		"unicast">--
--<OSS.DefineName
--		MULTIMEDIA-SYSTEM-CONTROL.NetworkAccessParameters.distribution.unicast
--		"EM_unicast">--
--<OSS.FIELDNAME
--		MULTIMEDIA-SYSTEM-CONTROL.NetworkAccessParameters.distribution.multicast
--		"multicast">--
--<OSS.DefineName
--		MULTIMEDIA-SYSTEM-CONTROL.NetworkAccessParameters.distribution.multicast
--		"EM_multicast">--

--<OSS.ExtractType
--		MULTIMEDIA-SYSTEM-CONTROL.NetworkAccessParameters.networkAddress>--
--<OSS.TYPENAME
--		MULTIMEDIA-SYSTEM-CONTROL.NetworkAccessParameters.networkAddress
--		"EmNetworkAddress">--
--<OSS.FIELDNAME
--		MULTIMEDIA-SYSTEM-CONTROL.NetworkAccessParameters.networkAddress
--		"networkAddress">--
--<OSS.FIELDNAME
--		MULTIMEDIA-SYSTEM-CONTROL.NetworkAccessParameters.networkAddress.q2931Address
--		"q2931Address">--
--<OSS.DefineName
--		MULTIMEDIA-SYSTEM-CONTROL.NetworkAccessParameters.networkAddress.q2931Address
--		"EM_q2931Address">--
--<OSS.FIELDNAME
--		MULTIMEDIA-SYSTEM-CONTROL.NetworkAccessParameters.networkAddress.e164Address
--		"e164Address">--
--<OSS.DefineName
--		MULTIMEDIA-SYSTEM-CONTROL.NetworkAccessParameters.networkAddress.e164Address
--		"EM_e164Address">--
--<OSS.FIELDNAME
--		MULTIMEDIA-SYSTEM-CONTROL.NetworkAccessParameters.networkAddress.localAreaAddress
--		"localAreaAddress">--
--<OSS.DefineName
--		MULTIMEDIA-SYSTEM-CONTROL.NetworkAccessParameters.networkAddress.localAreaAddress
--		"EM_localAreaAddress">--

--<OSS.FIELDNAME
--		MULTIMEDIA-SYSTEM-CONTROL.NetworkAccessParameters.associateConference
--		"associateConference">--

--<OSS.ExtractType
--		MULTIMEDIA-SYSTEM-CONTROL.NetworkAccessParameters.externalReference>--
--<OSS.TYPENAME
--		MULTIMEDIA-SYSTEM-CONTROL.NetworkAccessParameters.externalReference
--		"EmExternalReference">--
--<OSS.FIELDNAME
--		MULTIMEDIA-SYSTEM-CONTROL.NetworkAccessParameters.externalReference
--		"externalReference">--
--<OSS.DefineName
--		MULTIMEDIA-SYSTEM-CONTROL.NetworkAccessParameters.externalReference
--		"EM_externalReference">--

--<OSS.ExtractType
--		MULTIMEDIA-SYSTEM-CONTROL.NetworkAccessParameters.t120SetupProcedure>--
--<OSS.TYPENAME
--		MULTIMEDIA-SYSTEM-CONTROL.NetworkAccessParameters.t120SetupProcedure
--		"EmT120SetupProcedure">--
--<OSS.FIELDNAME
--		MULTIMEDIA-SYSTEM-CONTROL.NetworkAccessParameters.t120SetupProcedure
--		"t120SetupProcedure">--
--<OSS.DefineName
--		MULTIMEDIA-SYSTEM-CONTROL.NetworkAccessParameters.t120SetupProcedure
--		"EM_t120SetupProcedure">--
--<OSS.FIELDNAME
--		MULTIMEDIA-SYSTEM-CONTROL.NetworkAccessParameters.t120SetupProcedure.originateCall
--		"originateCall">--
--<OSS.DefineName
--		MULTIMEDIA-SYSTEM-CONTROL.NetworkAccessParameters.t120SetupProcedure.originateCall
--		"EM_originateCall">--
--<OSS.FIELDNAME
--		MULTIMEDIA-SYSTEM-CONTROL.NetworkAccessParameters.t120SetupProcedure.waitForCall
--		"waitForCall">--
--<OSS.DefineName
--		MULTIMEDIA-SYSTEM-CONTROL.NetworkAccessParameters.t120SetupProcedure.waitForCall
--		"EM_waitForCall">--
--<OSS.FIELDNAME
--		MULTIMEDIA-SYSTEM-CONTROL.NetworkAccessParameters.t120SetupProcedure.issueQuery
--		"issueQuery">--
--<OSS.DefineName
--		MULTIMEDIA-SYSTEM-CONTROL.NetworkAccessParameters.t120SetupProcedure.issueQuery
--		"EM_issueQuery">--

-- -------------------------------------------------------------- --
--  
-- Q2931Address    ::= SEQUENCE
-- {
--     address CHOICE
--     {
--         internationalNumber NumericString(SIZE(1..16)),
--         nsapAddress OCTET STRING (SIZE(1..20)),
--         ...
--     },
--     subaddress  OCTET STRING (SIZE(1..20)) OPTIONAL,
--     ...
-- }
--
-- -------------------------------------------------------------- --

--<ASN1.PDU 
--		MULTIMEDIA-SYSTEM-CONTROL.Q2931Address>--
--<OSS.TYPENAME
--		MULTIMEDIA-SYSTEM-CONTROL.Q2931Address
--		"EmQ2931Address">--

--<OSS.ExtractType
--		MULTIMEDIA-SYSTEM-CONTROL.Q2931Address.address>--
--<OSS.TYPENAME
--		MULTIMEDIA-SYSTEM-CONTROL.Q2931Address.address
--		"EmQ2931AddressChoice">--
--<OSS.FIELDNAME
--		MULTIMEDIA-SYSTEM-CONTROL.Q2931Address.address
--		"address">--
--<OSS.FIELDNAME
--		MULTIMEDIA-SYSTEM-CONTROL.Q2931Address.address.internationalNumber
--		"internationalNumber">--
--<OSS.DefineName
--		MULTIMEDIA-SYSTEM-CONTROL.Q2931Address.address.internationalNumber
--		"EM_Q2931_internationalNumber">--

--<OSS.InlineType
--		MULTIMEDIA-SYSTEM-CONTROL.Q2931Address.address>--
--<OSS.TYPENAME
--		MULTIMEDIA-SYSTEM-CONTROL.Q2931Address.address.nsapAddress
--		"EmQ2931NsapAddress">--
--<OSS.FIELDNAME
--		MULTIMEDIA-SYSTEM-CONTROL.Q2931Address.address.nsapAddress
--		"nsapAddress">--
--<OSS.DefineName
--		MULTIMEDIA-SYSTEM-CONTROL.Q2931Address.address.nsapAddress
--		"EM_Q2931_nsapAddress">--

--<OSS.InlineType
--		MULTIMEDIA-SYSTEM-CONTROL.Q2931Address.subaddress>--
--<OSS.TYPENAME
--		MULTIMEDIA-SYSTEM-CONTROL.Q2931Address.subaddress
--		"EmQ2931Subaddress">--
--<OSS.FIELDNAME
--		MULTIMEDIA-SYSTEM-CONTROL.Q2931Address.subaddress
--		"subaddress">--
--<OSS.DefineName
--		MULTIMEDIA-SYSTEM-CONTROL.Q2931Address.subaddress
--		"EM_subaddress">--

-- -------------------------------------------------------------- --
--  
-- V75Parameters   ::= SEQUENCE
-- {
--     audioHeaderPresent  BOOLEAN,
--      ...
-- }
--
-- -------------------------------------------------------------- --

--<ASN1.PDU 
--		MULTIMEDIA-SYSTEM-CONTROL.V75Parameters>--
--<OSS.TYPENAME
--		MULTIMEDIA-SYSTEM-CONTROL.V75Parameters
--		"EmV75Parameters">--
--<OSS.FIELDNAME
--		MULTIMEDIA-SYSTEM-CONTROL.V75Parameters.audioHeaderPresent
--		"audioHeaderPresent">--

-- -------------------------------------------------------------- --
--  
-- DataType        ::= CHOICE
-- {
--     nonStandard     NonStandardParameter,
--     nullData        NULL,
--     videoData       VideoCapability,
--     audioData       AudioCapability,
--     data            DataApplicationCapability,
--     encryptionData  EncryptionMode,
--     ...,
--     h235Control     NonStandardParameter,
--     h235Media       H235Media
-- }
--
-- -------------------------------------------------------------- --

--<ASN1.PDU 
--		MULTIMEDIA-SYSTEM-CONTROL.DataType>--
--<OSS.TYPENAME
--		MULTIMEDIA-SYSTEM-CONTROL.DataType
--		"EmDataType">--
--<OSS.FIELDNAME
--		MULTIMEDIA-SYSTEM-CONTROL.DataType.nonStandard
--		"nonStandard">--
--<OSS.DefineName
--		MULTIMEDIA-SYSTEM-CONTROL.DataType.nonStandard
--		"EM_DataType_nonStandard">--
--<OSS.FIELDNAME
--		MULTIMEDIA-SYSTEM-CONTROL.DataType.nullData
--		"nullData">--
--<OSS.DefineName
--		MULTIMEDIA-SYSTEM-CONTROL.DataType.nullData
--		"EM_nullData">--
--<OSS.FIELDNAME
--		MULTIMEDIA-SYSTEM-CONTROL.DataType.videoData
--		"videoData">--
--<OSS.DefineName
--		MULTIMEDIA-SYSTEM-CONTROL.DataType.videoData
--		"EM_DataType_videoData">--
--<OSS.FIELDNAME
--		MULTIMEDIA-SYSTEM-CONTROL.DataType.audioData
--		"audioData">--
--<OSS.DefineName
--		MULTIMEDIA-SYSTEM-CONTROL.DataType.audioData
--		"EM_DataType_audioData">--
--<OSS.FIELDNAME
--		MULTIMEDIA-SYSTEM-CONTROL.DataType.data
--		"data">--
--<OSS.DefineName
--		MULTIMEDIA-SYSTEM-CONTROL.DataType.data
--		"EM_DataType_data">--
--<OSS.FIELDNAME
--		MULTIMEDIA-SYSTEM-CONTROL.DataType.encryptionData
--		"encryptionData">--
--<OSS.DefineName
--		MULTIMEDIA-SYSTEM-CONTROL.DataType.encryptionData
--		"EM_encryptionData">--
--<OSS.FIELDNAME
--		MULTIMEDIA-SYSTEM-CONTROL.DataType.h235Control
--		"h235Control">--
--<OSS.DefineName
--		MULTIMEDIA-SYSTEM-CONTROL.DataType.h235Control
--		"EM_h235Control">--
--<OSS.FIELDNAME
--		MULTIMEDIA-SYSTEM-CONTROL.DataType.h235Media
--		"h235Media">--
--<OSS.DefineName
--		MULTIMEDIA-SYSTEM-CONTROL.DataType.h235Media
--		"EM_h235Media">--

-- -------------------------------------------------------------- --
--  
-- H235Media ::= SEQUENCE
-- {
--     encryptionAuthenticationAndIntegrity    EncryptionAuthenticationAndIntegrity,
--  
--     mediaType   CHOICE
--     {
--         nonStandard NonStandardParameter,
--         videoData   VideoCapability,
--         audioData   AudioCapability,
--         data        DataApplicationCapability,
--         ...
--     },
--     ...
-- }
--
-- -------------------------------------------------------------- --

--<ASN1.PDU 
--		MULTIMEDIA-SYSTEM-CONTROL.H235Media>--
--<OSS.TYPENAME
--		MULTIMEDIA-SYSTEM-CONTROL.H235Media
--		"EmH235Media">--
--<OSS.FIELDNAME
--		MULTIMEDIA-SYSTEM-CONTROL.H235Media.encryptionAuthenticationAndIntegrity
--		"encryptionAuthenticationAndIntegrity">--

--<OSS.ExtractType
--		MULTIMEDIA-SYSTEM-CONTROL.H235Media.mediaType>--
--<OSS.TYPENAME
--		MULTIMEDIA-SYSTEM-CONTROL.H235Media.mediaType
--		"EmMediaType">--
--<OSS.FIELDNAME
--		MULTIMEDIA-SYSTEM-CONTROL.H235Media.mediaType
--		"mediaType">--
--<OSS.FIELDNAME
--		MULTIMEDIA-SYSTEM-CONTROL.H235Media.mediaType.nonStandard
--		"nonStandard">--
--<OSS.DefineName
--		MULTIMEDIA-SYSTEM-CONTROL.H235Media.mediaType.nonStandard
--		"EM_MediaType_nonStandard">--
--<OSS.FIELDNAME
--		MULTIMEDIA-SYSTEM-CONTROL.H235Media.mediaType.videoData
--		"videoData">--
--<OSS.DefineName
--		MULTIMEDIA-SYSTEM-CONTROL.H235Media.mediaType.videoData
--		"EM_MediaType_videoData">--
--<OSS.FIELDNAME
--		MULTIMEDIA-SYSTEM-CONTROL.H235Media.mediaType.audioData
--		"audioData">--
--<OSS.DefineName
--		MULTIMEDIA-SYSTEM-CONTROL.H235Media.mediaType.audioData
--		"EM_MediaType_audioData">--
--<OSS.FIELDNAME
--		MULTIMEDIA-SYSTEM-CONTROL.H235Media.mediaType.data
--		"data">--
--<OSS.DefineName
--		MULTIMEDIA-SYSTEM-CONTROL.H235Media.mediaType.data
--		"EM_MediaType_data">--

-- -------------------------------------------------------------- --
--  
-- H222LogicalChannelParameters    ::= SEQUENCE
-- {
--     resourceID          INTEGER (0..65535),
--     subChannelID        INTEGER (0..8191),
--     pcr-pid             INTEGER (0..8191)  OPTIONAL,
--     programDescriptors  OCTET STRING  OPTIONAL,
--     streamDescriptors   OCTET STRING  OPTIONAL,
--     ...
-- }
--
-- -------------------------------------------------------------- --

--<ASN1.Remove
--		MULTIMEDIA-SYSTEM-CONTROL.H222LogicalChannelParameters>--

-- -------------------------------------------------------------- --
--
-- H223LogicalChannelParameters    ::= SEQUENCE
-- {
--     adaptationLayerType CHOICE
--     {
--         nonStandard                 NonStandardParameter,
--         al1Framed                   NULL,
--         al1NotFramed                NULL,
--         al2WithoutSequenceNumbers   NULL,
--         al2WithSequenceNumbers      NULL,
--         al3     SEQUENCE
--         {
--             controlFieldOctets  INTEGER (0..2),
--             sendBufferSize      INTEGER (0..16777215)
--         },
--         ...,
--         al1M    H223AL1MParameters,
--         al2M    H223AL2MParameters,
--         al3M    H223AL3MParameters
--     },
--  
--     segmentableFlag BOOLEAN,
--     ...
-- }
--
-- -------------------------------------------------------------- --

--<ASN1.Remove
--		MULTIMEDIA-SYSTEM-CONTROL.H223LogicalChannelParameters>--

-- -------------------------------------------------------------- --
--
-- H223AL1MParameters ::= SEQUENCE
-- {
--     transferMode    CHOICE
--     {
--         framed      NULL,
--         unframed    NULL,
--         ...
--     },
--     headerFEC   CHOICE
--     {
--         sebch16-7   NULL,
--         golay24-12  NULL,
--         ...
--     },
--     crcLength   CHOICE
--     {
--         crc4bit     NULL,
--         crc12bit    NULL,
--         crc20bit    NULL,
--         crc28bit    NULL,
--         ...
--     },
--  
--     rcpcCodeRate    INTEGER (8..32),
--  
--     arqType CHOICE
--     {
--         noArq       NULL,
--         typeIArq    H223AnnexCArqParameters,
--         typeIIArq   H223AnnexCArqParameters,
--         ...
--     },
--     alpduInterleaving   BOOLEAN,
--     alsduSplitting      BOOLEAN,
--     ...
-- }
--  
-- -------------------------------------------------------------- --

--<ASN1.Remove
--		MULTIMEDIA-SYSTEM-CONTROL.H223AL1MParameters>--

-- -------------------------------------------------------------- --
--
-- H223AL2MParameters ::= SEQUENCE
-- {
--     headerFEC   CHOICE
--     {
--         sebch16-5   NULL,
--         golay24-12  NULL,
--         ...
--     },
--     alpduInterleaving   BOOLEAN,
--     ...
-- }
--  
-- -------------------------------------------------------------- --

--<ASN1.Remove
--		MULTIMEDIA-SYSTEM-CONTROL.H223AL2MParameters>--

-- -------------------------------------------------------------- --
--  
-- H223AL3MParameters ::= SEQUENCE
-- {
--     headerFormat    CHOICE
--     {
--         sebch16-7   NULL,
--         golay24-12  NULL,
--         ...
--     },
--     crcLength   CHOICE
--     {
--         crc4bit     NULL,
--         crc12bit    NULL,
--         crc20bit    NULL,
--         crc28bit    NULL,
--         ...
--     },
--  
--     rcpcCodeRate    INTEGER (8..32),
--  
--     arqType CHOICE
--     {
--         noArq       NULL,
--         typeIArq    H223AnnexCArqParameters,
--         typeIIArq   H223AnnexCArqParameters,
--         ...
--     },
--  
--     alpduInterleaving   BOOLEAN,
--     ...
-- }
--
-- -------------------------------------------------------------- --

--<ASN1.Remove
--		MULTIMEDIA-SYSTEM-CONTROL.H223AL3MParameters>--

-- -------------------------------------------------------------- --
--
-- H223AnnexCArqParameters ::= SEQUENCE
-- {
--     numberOfRetransmissions CHOICE
--     {
--         finite      INTEGER (0..16),
--         infinite    NULL,
--         ...
--     },
--     sendBufferSize  INTEGER (0..16777215),
--     ...
-- }
--
-- -------------------------------------------------------------- --

--<ASN1.Remove
--		MULTIMEDIA-SYSTEM-CONTROL.H223AnnexCArqParameters>--

-- -------------------------------------------------------------- --
--
-- V76LogicalChannelParameters ::= SEQUENCE
-- {
--     hdlcParameters  V76HDLCParameters,
--     suspendResume   CHOICE
--     {
--         noSuspendResume             NULL,
--         suspendResumewAddress       NULL,
--         suspendResumewoAddress      NULL,
--         ...
--     },
--     uIH         BOOLEAN,
--     mode        CHOICE
--     {
--         eRM SEQUENCE
--         {
--             windowSize  INTEGER (1..127),
--             recovery    CHOICE
--             {
--                 rej     NULL,
--                 sREJ    NULL,
--                 mSREJ   NULL,
--                 ...
--             },
--             ...
--         },
--         uNERM   NULL,
--         ...
--     },
--     v75Parameters   V75Parameters,
--     ...
-- }
--
-- -------------------------------------------------------------- --

--<ASN1.Remove
--		MULTIMEDIA-SYSTEM-CONTROL.V76LogicalChannelParameters>--

-- -------------------------------------------------------------- --
--
-- V76HDLCParameters   ::= SEQUENCE
-- {
--     crcLength   CRCLength,
--     n401        INTEGER (1..127),
--     loopbackTestProcedure   BOOLEAN,
--         ...
-- }
--
-- -------------------------------------------------------------- --
 
--<ASN1.Remove
--		MULTIMEDIA-SYSTEM-CONTROL.V76HDLCParameters>--

-- -------------------------------------------------------------- --
--
-- CRCLength   ::= CHOICE
-- {
--     crc8bit     NULL,
--     crc16bit    NULL,
--     crc32bit    NULL,
--     ...
-- }
--
-- -------------------------------------------------------------- --
 
--<ASN1.PDU
--		MULTIMEDIA-SYSTEM-CONTROL.CRCLength>--
--<OSS.TYPENAME
--		MULTIMEDIA-SYSTEM-CONTROL.CRCLength
--		"EmCRCLength">--
--<OSS.FIELDNAME
--		MULTIMEDIA-SYSTEM-CONTROL.CRCLength.crc8bit
--		"crc8bit">--
--<OSS.DefineName
--		MULTIMEDIA-SYSTEM-CONTROL.CRCLength.crc8bit
--		"EM_crc8bit">--
--<OSS.FIELDNAME
--		MULTIMEDIA-SYSTEM-CONTROL.CRCLength.crc16bit
--		"crc16bit">--
--<OSS.DefineName
--		MULTIMEDIA-SYSTEM-CONTROL.CRCLength.crc16bit
--		"EM_crc16bit">--
--<OSS.FIELDNAME
--		MULTIMEDIA-SYSTEM-CONTROL.CRCLength.crc32bit
--		"crc32bit">--
--<OSS.DefineName
--		MULTIMEDIA-SYSTEM-CONTROL.CRCLength.crc32bit
--		"EM_crc32bit">--

-- -------------------------------------------------------------- --
--
-- H2250LogicalChannelParameters   ::= SEQUENCE
-- {
--     nonStandard                     SEQUENCE OF NonStandardParameter OPTIONAL,
--     sessionID                       INTEGER(0..255),
--     associatedSessionID             INTEGER(1..255)  OPTIONAL,
--     mediaChannel                    TransportAddress  OPTIONAL,
--     mediaGuaranteedDelivery         BOOLEAN  OPTIONAL,
--     mediaControlChannel             TransportAddress  OPTIONAL,
--     mediaControlGuaranteedDelivery  BOOLEAN  OPTIONAL,
--     silenceSuppression              BOOLEAN  OPTIONAL,
--     destination                     TerminalLabel OPTIONAL,
--  
--     dynamicRTPPayloadType           INTEGER(96..127)  OPTIONAL,
--     mediaPacketization  CHOICE
--     {
--         h261aVideoPacketization NULL,
--         ...,
--         rtpPayloadType          RTPPayloadType
--     } OPTIONAL,
--     ...,
--     transportCapability TransportCapability OPTIONAL,
--     redundancyEncoding  RedundancyEncoding OPTIONAL,
--     source              TerminalLabel OPTIONAL
-- }
--
-- -------------------------------------------------------------- --

--<ASN1.PDU
--		MULTIMEDIA-SYSTEM-CONTROL.H2250LogicalChannelParameters>--
--<OSS.TYPENAME
--		MULTIMEDIA-SYSTEM-CONTROL.H2250LogicalChannelParameters
--		"EmH2250LogicalChannelParameters">--
--<OSS.FIELDNAME
--		MULTIMEDIA-SYSTEM-CONTROL.H2250LogicalChannelParameters.nonStandard
--		"nonStandard">--
--<OSS.DefineName
--		MULTIMEDIA-SYSTEM-CONTROL.H2250LogicalChannelParameters.nonStandard
--		"EM_H2250LCP_nonStandard">--
--<OSS.FIELDNAME
--		MULTIMEDIA-SYSTEM-CONTROL.H2250LogicalChannelParameters.sessionID
--		"sessionID">--
--<OSS.FIELDNAME
--		MULTIMEDIA-SYSTEM-CONTROL.H2250LogicalChannelParameters.associatedSessionID
--		"associatedSessionID">--
--<OSS.DefineName
--		MULTIMEDIA-SYSTEM-CONTROL.H2250LogicalChannelParameters.associatedSessionID
--		"EM_H2250LCP_associatedSessionID">--
--<OSS.FIELDNAME
--		MULTIMEDIA-SYSTEM-CONTROL.H2250LogicalChannelParameters.mediaChannel
--		"mediaChannel">--
--<OSS.DefineName
--		MULTIMEDIA-SYSTEM-CONTROL.H2250LogicalChannelParameters.mediaChannel
--		"EM_H2250LCP_mediaChannel">--
--<OSS.FIELDNAME
--		MULTIMEDIA-SYSTEM-CONTROL.H2250LogicalChannelParameters.mediaGuaranteedDelivery
--		"mediaGuaranteedDelivery">--
--<OSS.DefineName
--		MULTIMEDIA-SYSTEM-CONTROL.H2250LogicalChannelParameters.mediaGuaranteedDelivery
--		"EM_H2250LCP_mediaGuaranteedDelivery">--
--<OSS.FIELDNAME
--		MULTIMEDIA-SYSTEM-CONTROL.H2250LogicalChannelParameters.mediaControlChannel
--		"mediaControlChannel">--
--<OSS.DefineName
--		MULTIMEDIA-SYSTEM-CONTROL.H2250LogicalChannelParameters.mediaControlChannel
--		"EM_H2250LCP_mediaControlChannel">--
--<OSS.FIELDNAME
--		MULTIMEDIA-SYSTEM-CONTROL.H2250LogicalChannelParameters.mediaControlGuaranteedDelivery
--		"mediaControlGuaranteedDelivery">--
--<OSS.DefineName
--		MULTIMEDIA-SYSTEM-CONTROL.H2250LogicalChannelParameters.mediaControlGuaranteedDelivery
--		"EM_H2250LCP_mediaControlGuaranteedDelivery">--
--<OSS.FIELDNAME
--		MULTIMEDIA-SYSTEM-CONTROL.H2250LogicalChannelParameters.silenceSuppression
--		"silenceSuppression">--
--<OSS.DefineName
--		MULTIMEDIA-SYSTEM-CONTROL.H2250LogicalChannelParameters.silenceSuppression
--		"EM_silenceSuppression">--
--<OSS.FIELDNAME
--		MULTIMEDIA-SYSTEM-CONTROL.H2250LogicalChannelParameters.destination
--		"destination">--
--<OSS.DefineName
--		MULTIMEDIA-SYSTEM-CONTROL.H2250LogicalChannelParameters.destination
--		"EM_H2250LCP_destination">--
--<OSS.FIELDNAME
--		MULTIMEDIA-SYSTEM-CONTROL.H2250LogicalChannelParameters.dynamicRTPPayloadType
--		"dynamicRTPPayloadType">--
--<OSS.DefineName
--		MULTIMEDIA-SYSTEM-CONTROL.H2250LogicalChannelParameters.dynamicRTPPayloadType
--		"EM_H2250LCP_dynamicRTPPayloadType">--
--<OSS.ExtractType
--		MULTIMEDIA-SYSTEM-CONTROL.H2250LogicalChannelParameters.mediaPacketization>--
--<OSS.TYPENAME
--		MULTIMEDIA-SYSTEM-CONTROL.H2250LogicalChannelParameters.mediaPacketization
--		"EmMediaPacketization">--
--<OSS.FIELDNAME
--		MULTIMEDIA-SYSTEM-CONTROL.H2250LogicalChannelParameters.mediaPacketization
--		"mediaPacketization">--
--<OSS.DefineName
--		MULTIMEDIA-SYSTEM-CONTROL.H2250LogicalChannelParameters.mediaPacketization
--		"EM_mediaPacketization">--
--<OSS.FIELDNAME
--		MULTIMEDIA-SYSTEM-CONTROL.H2250LogicalChannelParameters.mediaPacketization.h261aVideoPacketization
--		"h261aVideoPacketization">--
--<OSS.DefineName
--		MULTIMEDIA-SYSTEM-CONTROL.H2250LogicalChannelParameters.mediaPacketization.h261aVideoPacketization
--		"EM_h261aVideoPacketization">--
--<OSS.FIELDNAME
--		MULTIMEDIA-SYSTEM-CONTROL.H2250LogicalChannelParameters.mediaPacketization.rtpPayloadType
--		"rtpPayloadType">--
--<OSS.DefineName
--		MULTIMEDIA-SYSTEM-CONTROL.H2250LogicalChannelParameters.mediaPacketization.rtpPayloadType
--		"EM_rtpPayloadType">--
--<OSS.FIELDNAME
--		MULTIMEDIA-SYSTEM-CONTROL.H2250LogicalChannelParameters.transportCapability
--		"transportCapability">--
--<OSS.DefineName
--		MULTIMEDIA-SYSTEM-CONTROL.H2250LogicalChannelParameters.transportCapability
--		"EM_H2250LCP_transportCapability">--
--<OSS.FIELDNAME
--		MULTIMEDIA-SYSTEM-CONTROL.H2250LogicalChannelParameters.redundancyEncoding
--		"redundancyEncoding">--
--<OSS.DefineName
--		MULTIMEDIA-SYSTEM-CONTROL.H2250LogicalChannelParameters.redundancyEncoding
--		"EM_H2250LCP_redundancyEncoding">--
--<OSS.FIELDNAME
--		MULTIMEDIA-SYSTEM-CONTROL.H2250LogicalChannelParameters.source
--		"source">--
--<OSS.DefineName
--		MULTIMEDIA-SYSTEM-CONTROL.H2250LogicalChannelParameters.source
--		"EM_source">--

-- -------------------------------------------------------------- --
--
-- RTPPayloadType ::= SEQUENCE
-- {
--     payloadDescriptor   CHOICE
--     {
--         nonStandardIdentifier   NonStandardParameter,
--         rfc-number              INTEGER (1..32768, ...),
--         oid                     OBJECT IDENTIFIER,
--         ...
--     },
--     payloadType INTEGER (0..127) OPTIONAL,
--     ...
-- }
--
-- -------------------------------------------------------------- --

--<ASN1.PDU
--		MULTIMEDIA-SYSTEM-CONTROL.RTPPayloadType>--
--<OSS.TYPENAME
--		MULTIMEDIA-SYSTEM-CONTROL.RTPPayloadType
--		"EmRTPPayloadType">--
--<OSS.ExtractType
--		MULTIMEDIA-SYSTEM-CONTROL.RTPPayloadType.payloadDescriptor>--
--<OSS.TYPENAME
--		MULTIMEDIA-SYSTEM-CONTROL.RTPPayloadType.payloadDescriptor
--		"EmPayloadDescriptor">--
--<OSS.FIELDNAME
--		MULTIMEDIA-SYSTEM-CONTROL.RTPPayloadType.payloadDescriptor
--		"payloadDescriptor">--
--<OSS.FIELDNAME
--		MULTIMEDIA-SYSTEM-CONTROL.RTPPayloadType.payloadDescriptor.nonStandardIdentifier
--		"nonStandardIdentifier">--
--<OSS.DefineName
--		MULTIMEDIA-SYSTEM-CONTROL.RTPPayloadType.payloadDescriptor.nonStandardIdentifier
--		"EM_nonStandardIdentifier">--
--<OSS.FIELDNAME
--		MULTIMEDIA-SYSTEM-CONTROL.RTPPayloadType.payloadDescriptor.rfc-number
--		"rfc_number">--
--<OSS.DefineName
--		MULTIMEDIA-SYSTEM-CONTROL.RTPPayloadType.payloadDescriptor.rfc-number
--		"EM_rfc_number">--
--<OSS.FIELDNAME
--		MULTIMEDIA-SYSTEM-CONTROL.RTPPayloadType.payloadDescriptor.oid
--		"oid">--
--<OSS.DefineName
--		MULTIMEDIA-SYSTEM-CONTROL.RTPPayloadType.payloadDescriptor.oid
--		"EM_oid">--
--<OSS.FIELDNAME
--		MULTIMEDIA-SYSTEM-CONTROL.RTPPayloadType.payloadType
--		"payloadType">--
--<OSS.DefineName
--		MULTIMEDIA-SYSTEM-CONTROL.RTPPayloadType.payloadType
--		"EM_payloadType">--

-- -------------------------------------------------------------- --
--
-- RedundancyEncoding ::= SEQUENCE
-- {
--     redundancyEncodingMethod    RedundancyEncodingMethod,
--     secondaryEncoding           DataType OPTIONAL,
--     ...
-- }
--
-- -------------------------------------------------------------- --

--<ASN1.PDU
--		MULTIMEDIA-SYSTEM-CONTROL.RedundancyEncoding>--
--<OSS.TYPENAME
--		MULTIMEDIA-SYSTEM-CONTROL.RedundancyEncoding
--		"EmRedundancyEncoding">--
--<OSS.FIELDNAME
--		MULTIMEDIA-SYSTEM-CONTROL.RedundancyEncoding.redundancyEncodingMethod
--		"redundancyEncodingMethod">--
--<OSS.FIELDNAME
--		MULTIMEDIA-SYSTEM-CONTROL.RedundancyEncoding.secondaryEncoding
--		"secondaryEncoding">--
--<OSS.DefineName
--		MULTIMEDIA-SYSTEM-CONTROL.RedundancyEncoding.secondaryEncoding
--		"EM_RedundancyEncoding_secondaryEncoding">--

-- -------------------------------------------------------------- --
--
-- TransportAddress    ::= CHOICE
-- {
--     unicastAddress  UnicastAddress,
--     multicastAddress    MulticastAddress,
--     ...
-- }
--
-- -------------------------------------------------------------- --

--<ASN1.PDU
--		MULTIMEDIA-SYSTEM-CONTROL.TransportAddress>--
--<OSS.TYPENAME
--		MULTIMEDIA-SYSTEM-CONTROL.TransportAddress
--		"EmH245TransportAddress">--
--<OSS.FIELDNAME
--		MULTIMEDIA-SYSTEM-CONTROL.TransportAddress.unicastAddress
--		"unicastAddress">--
--<OSS.DefineName
--		MULTIMEDIA-SYSTEM-CONTROL.TransportAddress.unicastAddress
--		"EM_unicastAddress">--
--<OSS.FIELDNAME
--		MULTIMEDIA-SYSTEM-CONTROL.TransportAddress.multicastAddress
--		"multicastAddress">--
--<OSS.DefineName
--		MULTIMEDIA-SYSTEM-CONTROL.TransportAddress.multicastAddress
--		"EM_multicastAddress">--

-- -------------------------------------------------------------- --
-- IP ::= OCTET STRING (SIZE(4))
-- -------------------------------------------------------------- --

--<OSS.TYPENAME 
--		MULTIMEDIA-SYSTEM-CONTROL.IP
--		"EmIP">--

-- -------------------------------------------------------------- --
-- IPAddress ::= SEQUENCE
-- {
-- 	network			IP,
-- 	tsapIdentifier	INTEGER(0..65535),
-- 	...
-- }
-- -------------------------------------------------------------- --

--<ASN1.PDU
--		MULTIMEDIA-SYSTEM-CONTROL.IPAddress>--
--<OSS.TYPENAME
--		MULTIMEDIA-SYSTEM-CONTROL.IPAddress
--		"EmH245IPAddress">--
--<OSS.FIELDNAME
--		MULTIMEDIA-SYSTEM-CONTROL.IPAddress.network
--		"network">--
--<OSS.FIELDNAME
--		MULTIMEDIA-SYSTEM-CONTROL.IPAddress.tsapIdentifier
--		"tsapIdentifier">--

-- -------------------------------------------------------------- --
-- IP6Address ::= SEQUENCE
-- {
-- 	network			OCTET STRING (SIZE(16)),
-- 	tsapIdentifier	INTEGER(0..65535), 
-- 	...
-- }
-- -------------------------------------------------------------- --

--<ASN1.PDU
--		MULTIMEDIA-SYSTEM-CONTROL.IP6Address>--
--<OSS.TYPENAME
--		MULTIMEDIA-SYSTEM-CONTROL.IP6Address
--		"EmH245IP6Address">--
--<OSS.InlineType
--		MULTIMEDIA-SYSTEM-CONTROL.IP6Address.network>--
--<OSS.TYPENAME
--		MULTIMEDIA-SYSTEM-CONTROL.IP6Address.network
--		"EmH245IP6">--
--<OSS.FIELDNAME
--		MULTIMEDIA-SYSTEM-CONTROL.IP6Address.network
--		"network">--
--<OSS.FIELDNAME
--		MULTIMEDIA-SYSTEM-CONTROL.IP6Address.tsapIdentifier
--		"tsapIdentifier">--

-- -------------------------------------------------------------- --
-- NSAPAddress ::= OCTET STRING (SIZE(1..20))
-- -------------------------------------------------------------- --

--<ASN1.PDU
--		MULTIMEDIA-SYSTEM-CONTROL.NSAPAddress>--
--<OSS.TYPENAME
--		MULTIMEDIA-SYSTEM-CONTROL.NSAPAddress
--		"EmH245NSAPAddress">--

-- -------------------------------------------------------------- --
--
-- UnicastAddress ::= CHOICE
-- {
-- 	iPAddress	IPAddress,
-- 	iPXAddress	SEQUENCE
-- 	{
-- 		node			OCTET STRING (SIZE(6)),
-- 		netnum			OCTET STRING (SIZE(4)),
-- 		tsapIdentifier	OCTET STRING (SIZE(2)),
-- 		...
-- 	},
-- 	iP6Address	IP6Address,
-- 	netBios				OCTET STRING (SIZE(16)),
-- 	iPSourceRouteAddress	SEQUENCE
-- 	{
-- 		routing	CHOICE
-- 		{
-- 			strict	NULL,
-- 			loose	NULL
-- 		},
-- 		network			IP,
-- 		tsapIdentifier	INTEGER(0..65535),
-- 		route			SEQUENCE OF IP,
-- 		...
-- 	},
-- 	...,
-- 	nsap				NSAPAddress,
-- 	nonStandardAddress	NonStandardParameter
-- }
--  
-- -------------------------------------------------------------- --

--<ASN1.PDU
--		MULTIMEDIA-SYSTEM-CONTROL.UnicastAddress>--
--<OSS.TYPENAME
--		MULTIMEDIA-SYSTEM-CONTROL.UnicastAddress
--		"EmUnicastAddress">--

--<OSS.FIELDNAME
--		MULTIMEDIA-SYSTEM-CONTROL.UnicastAddress.iPAddress
--		"iPAddress">--
--<OSS.DefineName
--		MULTIMEDIA-SYSTEM-CONTROL.UnicastAddress.iPAddress
--		"EM_Unicast_iPAddress">--

--<OSS.InlineType
--		MULTIMEDIA-SYSTEM-CONTROL.UnicastAddress.iPXAddress>--
--<OSS.TYPENAME
--		MULTIMEDIA-SYSTEM-CONTROL.UnicastAddress.iPXAddress
--		"EmH245IPXAddress">--
--<OSS.FIELDNAME
--		MULTIMEDIA-SYSTEM-CONTROL.UnicastAddress.iPXAddress
--		"iPXAddress">--
--<OSS.DefineName
--		MULTIMEDIA-SYSTEM-CONTROL.UnicastAddress.iPXAddress
--		"EM_Unicast_iPXAddress">--
--<OSS.InlineType
--		MULTIMEDIA-SYSTEM-CONTROL.UnicastAddress.iPXAddress.node>--
--<OSS.TYPENAME
--		MULTIMEDIA-SYSTEM-CONTROL.UnicastAddress.iPXAddress.node
--		"EMH245IPXNode">--
--<OSS.FIELDNAME
--		MULTIMEDIA-SYSTEM-CONTROL.UnicastAddress.iPXAddress.node
--		"node">--
--<OSS.InlineType
--		MULTIMEDIA-SYSTEM-CONTROL.UnicastAddress.iPXAddress.netnum>--
--<OSS.TYPENAME
--		MULTIMEDIA-SYSTEM-CONTROL.UnicastAddress.iPXAddress.netnum
--		"EMH245IPXNetnum">--
--<OSS.FIELDNAME
--		MULTIMEDIA-SYSTEM-CONTROL.UnicastAddress.iPXAddress.netnum
--		"netnum">--
--<OSS.InlineType
--		MULTIMEDIA-SYSTEM-CONTROL.UnicastAddress.iPXAddress.tsapIdentifier>--
--<OSS.TYPENAME
--		MULTIMEDIA-SYSTEM-CONTROL.UnicastAddress.iPXAddress.tsapIdentifier
--		"EMH245IPXTsapIdentifier">--
--<OSS.FIELDNAME
--		MULTIMEDIA-SYSTEM-CONTROL.UnicastAddress.iPXAddress.tsapIdentifier
--		"tsapIdentifier">--

--<OSS.FIELDNAME
--		MULTIMEDIA-SYSTEM-CONTROL.UnicastAddress.iP6Address
--		"iP6Address">--
--<OSS.DefineName
--		MULTIMEDIA-SYSTEM-CONTROL.UnicastAddress.iP6Address
--		"EM_Unicast_iP6Address">--

--<OSS.InlineType
--		MULTIMEDIA-SYSTEM-CONTROL.UnicastAddress.netBios>--
--<OSS.TYPENAME
--		MULTIMEDIA-SYSTEM-CONTROL.UnicastAddress.netBios
--		"EmH245NetBios">--
--<OSS.FIELDNAME
--		MULTIMEDIA-SYSTEM-CONTROL.UnicastAddress.netBios
--		"netBios">--
--<OSS.DefineName
--		MULTIMEDIA-SYSTEM-CONTROL.UnicastAddress.netBios
--		"EM_Unicast_netBios">--

--<OSS.InlineType
--		MULTIMEDIA-SYSTEM-CONTROL.UnicastAddress.iPSourceRouteAddress>--
--<OSS.TYPENAME
--		MULTIMEDIA-SYSTEM-CONTROL.UnicastAddress.iPSourceRouteAddress
--		"EmH245IPSourceRouteAddress">--
--<OSS.FIELDNAME
--		MULTIMEDIA-SYSTEM-CONTROL.UnicastAddress.iPSourceRouteAddress
--		"iPSourceRouteAddress">--
--<OSS.DefineName
--		MULTIMEDIA-SYSTEM-CONTROL.UnicastAddress.iPSourceRouteAddress
--		"EM_Unicast_iPSourceRouteAddress">--
--<OSS.ExtractType
--		MULTIMEDIA-SYSTEM-CONTROL.UnicastAddress.iPSourceRouteAddress.routing>--
--<OSS.TYPENAME
--		MULTIMEDIA-SYSTEM-CONTROL.UnicastAddress.iPSourceRouteAddress.routing
--		"EmH245Routing">--
--<OSS.FIELDNAME
--		MULTIMEDIA-SYSTEM-CONTROL.UnicastAddress.iPSourceRouteAddress.routing
--		"routing">--
--<OSS.FIELDNAME
--		MULTIMEDIA-SYSTEM-CONTROL.UnicastAddress.iPSourceRouteAddress.routing.strict
--		"strict">--
--<OSS.DefineName
--		MULTIMEDIA-SYSTEM-CONTROL.UnicastAddress.iPSourceRouteAddress.routing.strict
--		"EM_H245Routing_strict">--
--<OSS.FIELDNAME
--		MULTIMEDIA-SYSTEM-CONTROL.UnicastAddress.iPSourceRouteAddress.routing.loose
--		"loose">--
--<OSS.DefineName
--		MULTIMEDIA-SYSTEM-CONTROL.UnicastAddress.iPSourceRouteAddress.routing.loose
--		"EM_H245Routing_loose">--
--<OSS.FIELDNAME
--		MULTIMEDIA-SYSTEM-CONTROL.UnicastAddress.iPSourceRouteAddress.network
--		"network">--
--<OSS.FIELDNAME
--		MULTIMEDIA-SYSTEM-CONTROL.UnicastAddress.iPSourceRouteAddress.tsapIdentifier
--		"tsapIdentifier">--
--<OSS.ExtractType
--		MULTIMEDIA-SYSTEM-CONTROL.UnicastAddress.iPSourceRouteAddress.route>--
--<OSS.TYPENAME
--		MULTIMEDIA-SYSTEM-CONTROL.UnicastAddress.iPSourceRouteAddress.route
--		"EmSeqOfIP">--
--<OSS.FIELDNAME
--		MULTIMEDIA-SYSTEM-CONTROL.UnicastAddress.iPSourceRouteAddress.route
--		"route">--

--<OSS.FIELDNAME
--		MULTIMEDIA-SYSTEM-CONTROL.UnicastAddress.nsap
--		"nsap">--
--<OSS.DefineName
--		MULTIMEDIA-SYSTEM-CONTROL.UnicastAddress.nsap
--		"EM_Unicast_nsap">--

--<OSS.FIELDNAME
--		MULTIMEDIA-SYSTEM-CONTROL.UnicastAddress.nonStandardAddress
--		"nonStandardAddress">--
--<OSS.DefineName
--		MULTIMEDIA-SYSTEM-CONTROL.UnicastAddress.nonStandardAddress
--		"EM_Unicast_nonStandardAddress">--

-- -------------------------------------------------------------- --
--
-- MulticastAddress ::= CHOICE
-- {
-- 	iPAddress	SEQUENCE
-- 	{
-- 		network			IP,
-- 		tsapIdentifier	INTEGER(0..65535),
-- 		...
-- 	},
-- 	iP6Address	SEQUENCE
-- 	{
-- 		network			OCTET STRING (SIZE(16)),
-- 		tsapIdentifier	INTEGER(0..65535), 
-- 		...
-- 	},
-- 	...,
-- 	nsap				OCTET STRING (SIZE(1..20)),
-- 	nonStandardAddress	NonStandardParameter
-- }
--
-- -------------------------------------------------------------- --

--<ASN1.PDU
--		MULTIMEDIA-SYSTEM-CONTROL.MulticastAddress>--
--<OSS.TYPENAME
--		MULTIMEDIA-SYSTEM-CONTROL.MulticastAddress
--		"EmMulticastAddress">--

--<OSS.FIELDNAME
--		MULTIMEDIA-SYSTEM-CONTROL.MulticastAddress.iPAddress
--		"iPAddress">--
--<OSS.DefineName
--		MULTIMEDIA-SYSTEM-CONTROL.MulticastAddress.iPAddress
--		"EM_Multicast_iPAddress">--

--<OSS.FIELDNAME
--		MULTIMEDIA-SYSTEM-CONTROL.MulticastAddress.iP6Address
--		"iP6Address">--
--<OSS.DefineName
--		MULTIMEDIA-SYSTEM-CONTROL.MulticastAddress.iP6Address
--		"EM_Multicast_iP6Address">--

--<OSS.FIELDNAME
--		MULTIMEDIA-SYSTEM-CONTROL.MulticastAddress.nsap
--		"nsap">--
--<OSS.DefineName
--		MULTIMEDIA-SYSTEM-CONTROL.MulticastAddress.nsap
--		"EM_Multicast_nsap">--

--<OSS.FIELDNAME
--		MULTIMEDIA-SYSTEM-CONTROL.MulticastAddress.nonStandardAddress
--		"nonStandardAddress">--
--<OSS.DefineName
--		MULTIMEDIA-SYSTEM-CONTROL.MulticastAddress.nonStandardAddress
--		"EM_Multicast_nonStandardAddress">--

-- -------------------------------------------------------------- --
--
-- EncryptionSync ::= SEQUENCE
-- {
--     nonStandard             NonStandardParameter OPTIONAL,
--     synchFlag               INTEGER(0..255),
--  
--     h235Key                 OCTET STRING (SIZE(1..65535)),
-- 	   escrowentry			   SeqOf256EscrowData OPTIONAL,
--     ...
-- }
--
-- -------------------------------------------------------------- --

--<ASN1.PDU
--		MULTIMEDIA-SYSTEM-CONTROL.EncryptionSync>--
--<OSS.TYPENAME
--		MULTIMEDIA-SYSTEM-CONTROL.EncryptionSync
--		"EmEncryptionSync">--
--<OSS.FIELDNAME
--		MULTIMEDIA-SYSTEM-CONTROL.EncryptionSync.nonStandard
--		"nonStandard">--
--<OSS.DefineName
--		MULTIMEDIA-SYSTEM-CONTROL.EncryptionSync.nonStandard
--		"EM_EncryptionSync_nonStandard">--
--<OSS.FIELDNAME
--		MULTIMEDIA-SYSTEM-CONTROL.EncryptionSync.synchFlag
--		"synchFlag">--
--<OSS.UNBOUNDED
--		MULTIMEDIA-SYSTEM-CONTROL.EncryptionSync.h235Key>--
--<OSS.ExtractType
--		MULTIMEDIA-SYSTEM-CONTROL.EncryptionSync.h235Key>--
--<OSS.TYPENAME
--		MULTIMEDIA-SYSTEM-CONTROL.EncryptionSync.h235Key
--		"EmH235KeyString">--
--<OSS.FIELDNAME
--		MULTIMEDIA-SYSTEM-CONTROL.EncryptionSync.h235Key
--		"h235Key">--
--<OSS.FIELDNAME
--		MULTIMEDIA-SYSTEM-CONTROL.EncryptionSync.escrowentry
--		"escrowentry">--
--<OSS.DefineName
--		MULTIMEDIA-SYSTEM-CONTROL.EncryptionSync.escrowentry
--		"EM_escrowentry">--

-- -------------------------------------------------------------- --
--
-- EscrowData ::= SEQUENCE
-- {
--     escrowID        OBJECT IDENTIFIER,
--     escrowValue     BIT STRING (SIZE(1..65535)),
--     ...
-- }
--
-- -------------------------------------------------------------- --

--<ASN1.PDU
--		MULTIMEDIA-SYSTEM-CONTROL.EscrowData>--
--<OSS.TYPENAME
--		MULTIMEDIA-SYSTEM-CONTROL.EscrowData
--		"EmEscrowData">--
--<OSS.FIELDNAME
--		MULTIMEDIA-SYSTEM-CONTROL.EscrowData.escrowID
--		"escrowID">--
--<OSS.UNBOUNDED
--		MULTIMEDIA-SYSTEM-CONTROL.EscrowData.escrowValue>--
--<OSS.ExtractType
--		MULTIMEDIA-SYSTEM-CONTROL.EscrowData.escrowValue>--
--<OSS.TYPENAME
--		MULTIMEDIA-SYSTEM-CONTROL.EscrowData.escrowValue
--		"EmEscrowValue">--
--<OSS.FIELDNAME
--		MULTIMEDIA-SYSTEM-CONTROL.EscrowData.escrowValue
--		"escrowValue">--

-- -------------------------------------------------------------- --
--
-- OpenLogicalChannelAck   ::= SEQUENCE
-- {
--     forwardLogicalChannelNumber LogicalChannelNumber,
--  
--     reverseLogicalChannelParameters SEQUENCE
--     {
--         reverseLogicalChannelNumber LogicalChannelNumber,
--         portNumber  INTEGER (0..65535)  OPTIONAL,
--         multiplexParameters CHOICE
--         {
--             h222LogicalChannelParameters    H222LogicalChannelParameters,
--             ...,
--             h2250LogicalChannelParameters H2250LogicalChannelParameters
--  
--         }  OPTIONAL,
--         ...,
--         replacementFor  LogicalChannelNumber OPTIONAL
--  
--     }  OPTIONAL,
--     ...,
--     separateStack   NetworkAccessParameters  OPTIONAL,
--     forwardMultiplexAckParameters   CHOICE
--     {
--         h2250LogicalChannelAckParameters H2250LogicalChannelAckParameters,
--         ...
--     }  OPTIONAL
--     encryptionSync  EncryptionSync OPTIONAL
-- }
--
-- -------------------------------------------------------------- --

--<ASN1.PDU
--		MULTIMEDIA-SYSTEM-CONTROL.OpenLogicalChannelAck>--
--<OSS.TYPENAME
--		MULTIMEDIA-SYSTEM-CONTROL.OpenLogicalChannelAck
--		"EmOpenLogicalChannelAck">--
--<OSS.FIELDNAME
--		MULTIMEDIA-SYSTEM-CONTROL.OpenLogicalChannelAck.forwardLogicalChannelNumber
--		"forwardLogicalChannelNumber">--

--<OSS.ExtractType
--		MULTIMEDIA-SYSTEM-CONTROL.OpenLogicalChannelAck.reverseLogicalChannelParameters>--
--<OSS.TYPENAME
--		MULTIMEDIA-SYSTEM-CONTROL.OpenLogicalChannelAck.reverseLogicalChannelParameters
--		"EmOLCAReverseLogicalChannelParameters">--
--<OSS.FIELDNAME
--		MULTIMEDIA-SYSTEM-CONTROL.OpenLogicalChannelAck.reverseLogicalChannelParameters
--		"reverseLogicalChannelParameters">--
--<OSS.DefineName--
--		MULTIMEDIA-SYSTEM-CONTROL.OpenLogicalChannelAck.reverseLogicalChannelParameters
--		"EM_OLCA_reverseLogicalChannelParameters">--
--<OSS.FIELDNAME
--		MULTIMEDIA-SYSTEM-CONTROL.OpenLogicalChannelAck.reverseLogicalChannelParameters.reverseLogicalChannelNumber
--		"reverseLogicalChannelNumber">--
--<OSS.FIELDNAME
--		MULTIMEDIA-SYSTEM-CONTROL.OpenLogicalChannelAck.reverseLogicalChannelParameters.portNumber
--		"portNumber">--
--<OSS.DefineName
--		MULTIMEDIA-SYSTEM-CONTROL.OpenLogicalChannelAck.reverseLogicalChannelParameters.portNumber
--		"EM_OLCA_portNumber">--
--<OSS.ExtractType
--		MULTIMEDIA-SYSTEM-CONTROL.OpenLogicalChannelAck.reverseLogicalChannelParameters.multiplexParameters>--
--<OSS.TYPENAME
--		MULTIMEDIA-SYSTEM-CONTROL.OpenLogicalChannelAck.reverseLogicalChannelParameters.multiplexParameters
--		"EmOLCARevLCPMultiplexParameters">--
--<OSS.FIELDNAME
--		MULTIMEDIA-SYSTEM-CONTROL.OpenLogicalChannelAck.reverseLogicalChannelParameters.multiplexParameters
--		"multiplexParameters">--
--<OSS.DefineName
--		MULTIMEDIA-SYSTEM-CONTROL.OpenLogicalChannelAck.reverseLogicalChannelParameters.multiplexParameters
--		"EM_OLCA_multiplexParameters">--
--<ASN1.Remove
--		MULTIMEDIA-SYSTEM-CONTROL.OpenLogicalChannelAck.reverseLogicalChannelParameters.multiplexParameters.h222LogicalChannelParameters>--
--<OSS.FIELDNAME
--		MULTIMEDIA-SYSTEM-CONTROL.OpenLogicalChannelAck.reverseLogicalChannelParameters.multiplexParameters.h2250LogicalChannelParameters
--		"h2250LogicalChannelParameters">--
--<OSS.DefineName
--		MULTIMEDIA-SYSTEM-CONTROL.OpenLogicalChannelAck.reverseLogicalChannelParameters.multiplexParameters.h2250LogicalChannelParameters
--		"EM_OLCARevLCP_h2250LogicalChannelParameters">--
--<OSS.FIELDNAME
--		MULTIMEDIA-SYSTEM-CONTROL.OpenLogicalChannelAck.reverseLogicalChannelParameters.replacementFor
--		"replacementFor">--
--<OSS.DefineName
--		MULTIMEDIA-SYSTEM-CONTROL.OpenLogicalChannelAck.reverseLogicalChannelParameters.replacementFor
--		"EM_OLCA_replacementFor">--

--<OSS.FIELDNAME
--		MULTIMEDIA-SYSTEM-CONTROL.OpenLogicalChannelAck.separateStack
--		"separateStack">--
--<OSS.DefineName
--		MULTIMEDIA-SYSTEM-CONTROL.OpenLogicalChannelAck.separateStack
--		"EM_OLCA_separateStack">--

--<OSS.ExtractType
--		MULTIMEDIA-SYSTEM-CONTROL.OpenLogicalChannelAck.forwardMultiplexAckParameters>--
--<OSS.TYPENAME
--		MULTIMEDIA-SYSTEM-CONTROL.OpenLogicalChannelAck.forwardMultiplexAckParameters
--		"EmForwardMultiplexAckParameters">--
--<OSS.FIELDNAME
--		MULTIMEDIA-SYSTEM-CONTROL.OpenLogicalChannelAck.forwardMultiplexAckParameters
--		"forwardMultiplexAckParameters">--
--<OSS.DefineName
--		MULTIMEDIA-SYSTEM-CONTROL.OpenLogicalChannelAck.forwardMultiplexAckParameters
--		"EM_forwardMultiplexAckParameters">--
--<OSS.FIELDNAME
--		MULTIMEDIA-SYSTEM-CONTROL.OpenLogicalChannelAck.forwardMultiplexAckParameters.h2250LogicalChannelAckParameters
--		"h2250LogicalChannelAckParameters">--
--<OSS.DefineName
--		MULTIMEDIA-SYSTEM-CONTROL.OpenLogicalChannelAck.forwardMultiplexAckParameters.h2250LogicalChannelAckParameters
--		"EM_h2250LogicalChannelAckParameters">--

--<OSS.FIELDNAME
--		MULTIMEDIA-SYSTEM-CONTROL.OpenLogicalChannelAck.encryptionSync
--		"encryptionSync">--
--<OSS.DefineName
--		MULTIMEDIA-SYSTEM-CONTROL.OpenLogicalChannelAck.encryptionSync
--		"EM_OLCA_encryptionSync">--

-- -------------------------------------------------------------- --
--  
-- OpenLogicalChannelReject    ::= SEQUENCE
-- {
--     forwardLogicalChannelNumber LogicalChannelNumber,
--     cause       CHOICE
--     {
--         unspecified                         NULL,
--         unsuitableReverseParameters         NULL,
--         dataTypeNotSupported                NULL,
--         dataTypeNotAvailable                NULL,
--         unknownDataType                     NULL,
--         dataTypeALCombinationNotSupported   NULL,
--         ...,
--         multicastChannelNotAllowed          NULL,
--         insufficientBandwidth               NULL,
--         separateStackEstablishmentFailed    NULL,
--         invalidSessionID                    NULL,
--         masterSlaveConflict                 NULL
--         waitForCommunicationMode            NULL,
--         invalidDependentChannel             NULL,
--         replacementForRejected              NULL
--     },
--     ...
-- }
--
-- -------------------------------------------------------------- --

--<ASN1.PDU
--		MULTIMEDIA-SYSTEM-CONTROL.OpenLogicalChannelReject>--
--<OSS.TYPENAME
--		MULTIMEDIA-SYSTEM-CONTROL.OpenLogicalChannelReject
--		"EmOpenLogicalChannelReject">--
--<OSS.FIELDNAME
--		MULTIMEDIA-SYSTEM-CONTROL.OpenLogicalChannelReject.forwardLogicalChannelNumber
--		"forwardLogicalChannelNumber">--
--<OSS.ExtractType
--		MULTIMEDIA-SYSTEM-CONTROL.OpenLogicalChannelReject.cause>--
--<OSS.TYPENAME
--		MULTIMEDIA-SYSTEM-CONTROL.OpenLogicalChannelReject.cause
--		"EmOLCRejectCause">--
--<OSS.FIELDNAME
--		MULTIMEDIA-SYSTEM-CONTROL.OpenLogicalChannelReject.cause
--		"cause">--
--<OSS.FIELDNAME
--		MULTIMEDIA-SYSTEM-CONTROL.OpenLogicalChannelReject.cause.unspecified
--		"unspecified">--
--<OSS.DefineName
--		MULTIMEDIA-SYSTEM-CONTROL.OpenLogicalChannelReject.cause.unspecified
--		"EM_OLCRejectCause_unspecified">--
--<OSS.FIELDNAME
--		MULTIMEDIA-SYSTEM-CONTROL.OpenLogicalChannelReject.cause.unsuitableReverseParameters
--		"unsuitableReverseParameters">--
--<OSS.DefineName
--		MULTIMEDIA-SYSTEM-CONTROL.OpenLogicalChannelReject.cause.unsuitableReverseParameters
--		"EM_unsuitableReverseParameters">--
--<OSS.FIELDNAME
--		MULTIMEDIA-SYSTEM-CONTROL.OpenLogicalChannelReject.cause.dataTypeNotSupported
--		"dataTypeNotSupported">--
--<OSS.DefineName
--		MULTIMEDIA-SYSTEM-CONTROL.OpenLogicalChannelReject.cause.dataTypeNotSupported
--		"EM_dataTypeNotSupported">--
--<OSS.FIELDNAME
--		MULTIMEDIA-SYSTEM-CONTROL.OpenLogicalChannelReject.cause.dataTypeNotAvailable
--		"dataTypeNotAvailable">--
--<OSS.DefineName
--		MULTIMEDIA-SYSTEM-CONTROL.OpenLogicalChannelReject.cause.dataTypeNotAvailable
--		"EM_dataTypeNotAvailable">--
--<OSS.FIELDNAME
--		MULTIMEDIA-SYSTEM-CONTROL.OpenLogicalChannelReject.cause.unknownDataType
--		"unknownDataType">--
--<OSS.DefineName
--		MULTIMEDIA-SYSTEM-CONTROL.OpenLogicalChannelReject.cause.unknownDataType
--		"EM_unknownDataType">--
--<OSS.FIELDNAME
--		MULTIMEDIA-SYSTEM-CONTROL.OpenLogicalChannelReject.cause.dataTypeALCombinationNotSupported
--		"dataTypeALCombinationNotSupported">--
--<OSS.DefineName
--		MULTIMEDIA-SYSTEM-CONTROL.OpenLogicalChannelReject.cause.dataTypeALCombinationNotSupported
--		"EM_dataTypeALCombinationNotSupported">--
--<OSS.FIELDNAME
--		MULTIMEDIA-SYSTEM-CONTROL.OpenLogicalChannelReject.cause.multicastChannelNotAllowed
--		"multicastChannelNotAllowed">--
--<OSS.DefineName
--		MULTIMEDIA-SYSTEM-CONTROL.OpenLogicalChannelReject.cause.multicastChannelNotAllowed
--		"EM_multicastChannelNotAllowed">--
--<OSS.FIELDNAME
--		MULTIMEDIA-SYSTEM-CONTROL.OpenLogicalChannelReject.cause.insufficientBandwidth
--		"insufficientBandwidth">--
--<OSS.DefineName
--		MULTIMEDIA-SYSTEM-CONTROL.OpenLogicalChannelReject.cause.insufficientBandwidth
--		"EM_insufficientBandwidth">--
--<OSS.FIELDNAME
--		MULTIMEDIA-SYSTEM-CONTROL.OpenLogicalChannelReject.cause.separateStackEstablishmentFailed
--		"separateStackEstablishmentFailed">--
--<OSS.DefineName
--		MULTIMEDIA-SYSTEM-CONTROL.OpenLogicalChannelReject.cause.separateStackEstablishmentFailed
--		"EM_separateStackEstablishmentFailed">--
--<OSS.FIELDNAME
--		MULTIMEDIA-SYSTEM-CONTROL.OpenLogicalChannelReject.cause.invalidSessionID
--		"invalidSessionID">--
--<OSS.DefineName
--		MULTIMEDIA-SYSTEM-CONTROL.OpenLogicalChannelReject.cause.invalidSessionID
--		"EM_invalidSessionID">--
--<OSS.FIELDNAME
--		MULTIMEDIA-SYSTEM-CONTROL.OpenLogicalChannelReject.cause.masterSlaveConflict
--		"masterSlaveConflict">--
--<OSS.DefineName
--		MULTIMEDIA-SYSTEM-CONTROL.OpenLogicalChannelReject.cause.masterSlaveConflict
--		"EM_masterSlaveConflict">--
--<OSS.FIELDNAME
--		MULTIMEDIA-SYSTEM-CONTROL.OpenLogicalChannelReject.cause.waitForCommunicationMode
--		"waitForCommunicationMode">--
--<OSS.DefineName
--		MULTIMEDIA-SYSTEM-CONTROL.OpenLogicalChannelReject.cause.waitForCommunicationMode
--		"EM_waitForCommunicationMode">--
--<OSS.FIELDNAME
--		MULTIMEDIA-SYSTEM-CONTROL.OpenLogicalChannelReject.cause.invalidDependentChannel
--		"invalidDependentChannel">--
--<OSS.DefineName
--		MULTIMEDIA-SYSTEM-CONTROL.OpenLogicalChannelReject.cause.invalidDependentChannel
--		"EM_invalidDependentChannel">--
--<OSS.FIELDNAME
--		MULTIMEDIA-SYSTEM-CONTROL.OpenLogicalChannelReject.cause.replacementForRejected
--		"replacementForRejected">--
--<OSS.DefineName
--		MULTIMEDIA-SYSTEM-CONTROL.OpenLogicalChannelReject.cause.replacementForRejected
--		"EM_replacementForRejected">--

-- -------------------------------------------------------------- --
--  
-- OpenLogicalChannelConfirm   ::= SEQUENCE
-- {
--     forwardLogicalChannelNumber LogicalChannelNumber,
--     ...
-- }
--
-- -------------------------------------------------------------- --

--<ASN1.PDU
--		MULTIMEDIA-SYSTEM-CONTROL.OpenLogicalChannelConfirm>--
--<OSS.TYPENAME
--		MULTIMEDIA-SYSTEM-CONTROL.OpenLogicalChannelConfirm
--		"EmOpenLogicalChannelConfirm">--
--<OSS.FIELDNAME
--		MULTIMEDIA-SYSTEM-CONTROL.OpenLogicalChannelConfirm.forwardLogicalChannelNumber
--		"forwardLogicalChannelNumber">--

-- -------------------------------------------------------------- --
--  
-- H2250LogicalChannelAckParameters    ::= SEQUENCE
-- {
--     nonStandard             SEQUENCE OF NonStandardParameter  OPTIONAL,
--     sessionID               INTEGER(1..255)  OPTIONAL,
--     mediaChannel            TransportAddress  OPTIONAL,
--     mediaControlChannel     TransportAddress  OPTIONAL,
--     dynamicRTPPayloadType   INTEGER(96..127)  OPTIONAL,
--     ...,
--     flowControlToZero       BOOLEAN,
--	   portNumber			   INTEGER(0..65535) OPTIONAL
-- }
--
-- -------------------------------------------------------------- --

--<ASN1.PDU
--		MULTIMEDIA-SYSTEM-CONTROL.H2250LogicalChannelAckParameters>--
--<OSS.TYPENAME
--		MULTIMEDIA-SYSTEM-CONTROL.H2250LogicalChannelAckParameters
--		"EmH2250LogicalChannelAckParameters">--
--<OSS.FIELDNAME
--		MULTIMEDIA-SYSTEM-CONTROL.H2250LogicalChannelAckParameters.nonStandard
--		"nonStandard">--
--<OSS.DefineName
--		MULTIMEDIA-SYSTEM-CONTROL.H2250LogicalChannelAckParameters.nonStandard
--		"EM_H2250LCAP_nonStandard">--
--<OSS.FIELDNAME
--		MULTIMEDIA-SYSTEM-CONTROL.H2250LogicalChannelAckParameters.sessionID
--		"sessionID">--
--<OSS.DefineName
--		MULTIMEDIA-SYSTEM-CONTROL.H2250LogicalChannelAckParameters.sessionID
--		"EM_sessionID">--
--<OSS.FIELDNAME
--		MULTIMEDIA-SYSTEM-CONTROL.H2250LogicalChannelAckParameters.mediaChannel
--		"mediaChannel">--
--<OSS.DefineName
--		MULTIMEDIA-SYSTEM-CONTROL.H2250LogicalChannelAckParameters.mediaChannel
--		"EM_H2250LCAP_mediaChannel">--
--<OSS.FIELDNAME
--		MULTIMEDIA-SYSTEM-CONTROL.H2250LogicalChannelAckParameters.mediaControlChannel
--		"mediaControlChannel">--
--<OSS.DefineName
--		MULTIMEDIA-SYSTEM-CONTROL.H2250LogicalChannelAckParameters.mediaControlChannel
--		"EM_H2250LCAP_mediaControlChannel">--
--<OSS.FIELDNAME
--		MULTIMEDIA-SYSTEM-CONTROL.H2250LogicalChannelAckParameters.dynamicRTPPayloadType
--		"dynamicRTPPayloadType">--
--<OSS.DefineName
--		MULTIMEDIA-SYSTEM-CONTROL.H2250LogicalChannelAckParameters.dynamicRTPPayloadType
--		"EM_H2250LCAP_dynamicRTPPayloadType">--
--<OSS.FIELDNAME
--		MULTIMEDIA-SYSTEM-CONTROL.H2250LogicalChannelAckParameters.flowControlToZero
--		"flowControlToZero">--
--<OSS.DefineName
--		MULTIMEDIA-SYSTEM-CONTROL.H2250LogicalChannelAckParameters.flowControlToZero
--		"EM_flowControlToZero">--
--<OSS.FIELDNAME
--		MULTIMEDIA-SYSTEM-CONTROL.H2250LogicalChannelAckParameters.portNumber
--		"portNumber">--
--<OSS.DefineName
--		MULTIMEDIA-SYSTEM-CONTROL.H2250LogicalChannelAckParameters.portNumber
--		"EM_H2250LCAP_portNumber">--

-- -------------------------------------------------------------- --
--  
-- CloseLogicalChannel ::= SEQUENCE
-- {
--     forwardLogicalChannelNumber LogicalChannelNumber,
--     source      CHOICE
--     {
--         user    NULL,
--         lcse    NULL
--     },
--     ...,
--     reason      CHOICE
--     {
--         unknown             NULL,
--         reopen              NULL,
--         reservationFailure  NULL,
--         ...
--     }
--
-- -------------------------------------------------------------- --

--<ASN1.PDU
--		MULTIMEDIA-SYSTEM-CONTROL.CloseLogicalChannel>--
--<OSS.TYPENAME
--		MULTIMEDIA-SYSTEM-CONTROL.CloseLogicalChannel
--		"EmCloseLogicalChannel">--
--<OSS.FIELDNAME
--		MULTIMEDIA-SYSTEM-CONTROL.CloseLogicalChannel.forwardLogicalChannelNumber
--		"forwardLogicalChannelNumber">--
--<OSS.ExtractType
--		MULTIMEDIA-SYSTEM-CONTROL.CloseLogicalChannel.source>--
--<OSS.TYPENAME
--		MULTIMEDIA-SYSTEM-CONTROL.CloseLogicalChannel.source
--		"EmCLCSource">--
--<OSS.FIELDNAME
--		MULTIMEDIA-SYSTEM-CONTROL.CloseLogicalChannel.source
--		"source">--
--<OSS.FIELDNAME
--		MULTIMEDIA-SYSTEM-CONTROL.CloseLogicalChannel.source.user
--		"user">--
--<OSS.DefineName
--		MULTIMEDIA-SYSTEM-CONTROL.CloseLogicalChannel.source.user
--		"EM_user">--
--<OSS.FIELDNAME
--		MULTIMEDIA-SYSTEM-CONTROL.CloseLogicalChannel.source.lcse
--		"lcse">--
--<OSS.DefineName
--		MULTIMEDIA-SYSTEM-CONTROL.CloseLogicalChannel.source.lcse
--		"EM_lcse">--
--<OSS.ExtractType
--		MULTIMEDIA-SYSTEM-CONTROL.CloseLogicalChannel.reason>--
--<OSS.TYPENAME
--		MULTIMEDIA-SYSTEM-CONTROL.CloseLogicalChannel.reason
--		"EmCLCReason">--
--<OSS.FIELDNAME
--		MULTIMEDIA-SYSTEM-CONTROL.CloseLogicalChannel.reason
--		"reason">--
--<OSS.DefineName
--		MULTIMEDIA-SYSTEM-CONTROL.CloseLogicalChannel.reason
--		"EM_CLC_reason">--
--<OSS.FIELDNAME
--		MULTIMEDIA-SYSTEM-CONTROL.CloseLogicalChannel.reason.unknown
--		"unknown">--
--<OSS.DefineName
--		MULTIMEDIA-SYSTEM-CONTROL.CloseLogicalChannel.reason.unknown
--		"EM_CLCReason_unknown">--
--<OSS.FIELDNAME
--		MULTIMEDIA-SYSTEM-CONTROL.CloseLogicalChannel.reason.reopen
--		"reopen">--
--<OSS.DefineName
--		MULTIMEDIA-SYSTEM-CONTROL.CloseLogicalChannel.reason.reopen
--		"EM_CLCReason_reopen">--
--<OSS.FIELDNAME
--		MULTIMEDIA-SYSTEM-CONTROL.CloseLogicalChannel.reason.reservationFailure
--		"reservationFailure">--
--<OSS.DefineName
--		MULTIMEDIA-SYSTEM-CONTROL.CloseLogicalChannel.reason.reservationFailure
--		"EM_CLCReason_reservationFailure">--

-- -------------------------------------------------------------- --
--  
-- CloseLogicalChannelAck  ::= SEQUENCE
-- {
--     forwardLogicalChannelNumber LogicalChannelNumber,
--     ...
-- }
--
-- -------------------------------------------------------------- --

--<ASN1.PDU
--		MULTIMEDIA-SYSTEM-CONTROL.CloseLogicalChannelAck>--
--<OSS.TYPENAME
--		MULTIMEDIA-SYSTEM-CONTROL.CloseLogicalChannelAck
--		"EmCloseLogicalChannelAck">--
--<OSS.FIELDNAME
--		MULTIMEDIA-SYSTEM-CONTROL.CloseLogicalChannelAck.forwardLogicalChannelNumber
--		"forwardLogicalChannelNumber">--

-- -------------------------------------------------------------- --
--  
-- RequestChannelClose ::= SEQUENCE
-- {
--     forwardLogicalChannelNumber LogicalChannelNumber,
--     ...,
--     qosCapability               QOSCapability OPTIONAL,
--     reason      CHOICE
--     {
--         unknown             NULL,
--         normal              NULL,
--         reopen              NULL,
--         reservationFailure  NULL,
--         ...
--     }
-- }
--
-- -------------------------------------------------------------- --

--<ASN1.PDU
--		MULTIMEDIA-SYSTEM-CONTROL.RequestChannelClose>--
--<OSS.TYPENAME
--		MULTIMEDIA-SYSTEM-CONTROL.RequestChannelClose
--		"EmRequestChannelClose">--
--<OSS.FIELDNAME
--		MULTIMEDIA-SYSTEM-CONTROL.RequestChannelClose.forwardLogicalChannelNumber
--		"forwardLogicalChannelNumber">--
--<OSS.FIELDNAME
--		MULTIMEDIA-SYSTEM-CONTROL.RequestChannelClose.qosCapability
--		"qosCapability">--
--<OSS.DefineName
--		MULTIMEDIA-SYSTEM-CONTROL.RequestChannelClose.qosCapability
--		"EM_qosCapability">--
--<OSS.ExtractType
--		MULTIMEDIA-SYSTEM-CONTROL.RequestChannelClose.reason>--
--<OSS.TYPENAME
--		MULTIMEDIA-SYSTEM-CONTROL.RequestChannelClose.reason
--		"EmRCCReason">--
--<OSS.FIELDNAME
--		MULTIMEDIA-SYSTEM-CONTROL.RequestChannelClose.reason
--		"reason">--
--<OSS.DefineName
--		MULTIMEDIA-SYSTEM-CONTROL.RequestChannelClose.reason
--		"EM_RCC_reason">--
--<OSS.FIELDNAME
--		MULTIMEDIA-SYSTEM-CONTROL.RequestChannelClose.reason.unknown
--		"unknown">--
--<OSS.DefineName
--		MULTIMEDIA-SYSTEM-CONTROL.RequestChannelClose.reason.unknown
--		"EM_RCCReason_unknown">--
--<OSS.FIELDNAME
--		MULTIMEDIA-SYSTEM-CONTROL.RequestChannelClose.reason.normal
--		"normal">--
--<OSS.DefineName
--		MULTIMEDIA-SYSTEM-CONTROL.RequestChannelClose.reason.normal
--		"EM_normal">--
--<OSS.FIELDNAME
--		MULTIMEDIA-SYSTEM-CONTROL.RequestChannelClose.reason.reopen
--		"reopen">--
--<OSS.DefineName
--		MULTIMEDIA-SYSTEM-CONTROL.RequestChannelClose.reason.reopen
--		"EM_RCCReason_reopen">--
--<OSS.FIELDNAME
--		MULTIMEDIA-SYSTEM-CONTROL.RequestChannelClose.reason.reservationFailure
--		"reservationFailure">--
--<OSS.DefineName
--		MULTIMEDIA-SYSTEM-CONTROL.RequestChannelClose.reason.reservationFailure
--		"EM_RCCReason_reservationFailure">--

-- -------------------------------------------------------------- --
--  
-- RequestChannelCloseAck  ::= SEQUENCE
-- {
--     forwardLogicalChannelNumber LogicalChannelNumber,
--     ...
-- }
--
-- -------------------------------------------------------------- --

--<ASN1.PDU
--		MULTIMEDIA-SYSTEM-CONTROL.RequestChannelCloseAck>--
--<OSS.TYPENAME
--		MULTIMEDIA-SYSTEM-CONTROL.RequestChannelCloseAck
--		"EmRequestChannelCloseAck">--
--<OSS.FIELDNAME
--		MULTIMEDIA-SYSTEM-CONTROL.RequestChannelCloseAck.forwardLogicalChannelNumber
--		"forwardLogicalChannelNumber">--

-- -------------------------------------------------------------- --
--  
-- RequestChannelCloseReject   ::= SEQUENCE
-- {
--     forwardLogicalChannelNumber LogicalChannelNumber,
--     cause       CHOICE
--     {
--         unspecified NULL,
--         ...
--     },
--     ...
-- }
--
-- -------------------------------------------------------------- --

--<ASN1.PDU
--		MULTIMEDIA-SYSTEM-CONTROL.RequestChannelCloseReject>--
--<OSS.TYPENAME
--		MULTIMEDIA-SYSTEM-CONTROL.RequestChannelCloseReject
--		"EmRequestChannelCloseReject">--
--<OSS.FIELDNAME
--		MULTIMEDIA-SYSTEM-CONTROL.RequestChannelCloseReject.forwardLogicalChannelNumber
--		"forwardLogicalChannelNumber">--
--<OSS.FIELDNAME
--		MULTIMEDIA-SYSTEM-CONTROL.RequestChannelCloseReject.cause
--		"cause">--
--<OSS.ExtractType
--		MULTIMEDIA-SYSTEM-CONTROL.RequestChannelCloseReject.cause>--
--<OSS.TYPENAME
--		MULTIMEDIA-SYSTEM-CONTROL.RequestChannelCloseReject.cause
--		"EmRCCRejectCause">--
--<OSS.FIELDNAME
--		MULTIMEDIA-SYSTEM-CONTROL.RequestChannelCloseReject.cause.unspecified
--		"unspecified">--
--<OSS.DefineName
--		MULTIMEDIA-SYSTEM-CONTROL.RequestChannelCloseReject.cause.unspecified
--		"EM_RCCRejectCause_unspecified">--

-- -------------------------------------------------------------- --
--  
-- RequestChannelCloseRelease  ::= SEQUENCE
-- {
--     forwardLogicalChannelNumber LogicalChannelNumber,
--     ...
-- }
--
-- -------------------------------------------------------------- --

--<ASN1.PDU
--		MULTIMEDIA-SYSTEM-CONTROL.RequestChannelCloseRelease>--
--<OSS.TYPENAME
--		MULTIMEDIA-SYSTEM-CONTROL.RequestChannelCloseRelease
--		"EmRequestChannelCloseRelease">--
--<OSS.FIELDNAME
--		MULTIMEDIA-SYSTEM-CONTROL.RequestChannelCloseRelease.forwardLogicalChannelNumber
--		"forwardLogicalChannelNumber">--

-- ==============================================================
-- H.223 multiplex table definitions ** NOT IMPLEMENTED **
-- ==============================================================

-- -------------------------------------------------------------- --
--  
-- MultiplexEntrySend  ::= SEQUENCE
-- {
--     sequenceNumber  SequenceNumber,
--     multiplexEntryDescriptors   SET SIZE (1..15) OF MultiplexEntryDescriptor,
--     ...
-- }
--  
-- -------------------------------------------------------------- --

--<ASN1.Remove
--		MULTIMEDIA-SYSTEM-CONTROL.MultiplexEntrySend>--
 
-- -------------------------------------------------------------- --
--  
-- MultiplexEntryDescriptor    ::= SEQUENCE
-- {
--     multiplexTableEntryNumber   MultiplexTableEntryNumber,
--     elementList SEQUENCE SIZE (1..256) OF MultiplexElement OPTIONAL
-- }
--  
-- -------------------------------------------------------------- --

--<ASN1.Remove
--		MULTIMEDIA-SYSTEM-CONTROL.MultiplexEntryDescriptor>--

-- -------------------------------------------------------------- --
--  
-- MultiplexElement    ::= SEQUENCE
-- {
--     type        CHOICE
--     {
--         logicalChannelNumber    INTEGER(0..65535),
--         subElementList  SEQUENCE SIZE (2..255) OF MultiplexElement
--     },
--     repeatCount CHOICE
--     {
--         finite  INTEGER (1..65535),
--         untilClosingFlag    NULL
--     }
-- }
--  
-- -------------------------------------------------------------- --

--<ASN1.Remove
--		MULTIMEDIA-SYSTEM-CONTROL.MultiplexElement>--
 
-- -------------------------------------------------------------- --
--
-- MultiplexTableEntryNumber   ::=INTEGER (1..15)
--
-- -------------------------------------------------------------- --

--<ASN1.Remove
--		MULTIMEDIA-SYSTEM-CONTROL.MultiplexTableEntryNumber>--
 
-- -------------------------------------------------------------- --
--  
-- MultiplexEntrySendAck   ::= SEQUENCE
-- {
--     sequenceNumber  SequenceNumber,
--     multiplexTableEntryNumber   SET SIZE (1..15) OF MultiplexTableEntryNumber,
--     ...
-- }
--  
-- -------------------------------------------------------------- --

--<ASN1.Remove
--		MULTIMEDIA-SYSTEM-CONTROL.MultiplexEntrySendAck>--

-- -------------------------------------------------------------- --
--  
-- MultiplexEntrySendReject    ::= SEQUENCE
-- {
--     sequenceNumber  SequenceNumber,
--     rejectionDescriptions   SET SIZE (1..15) OF MultiplexEntryRejectionDescriptions,
--     ...
-- }
--  
-- -------------------------------------------------------------- --

--<ASN1.Remove
--		MULTIMEDIA-SYSTEM-CONTROL.MultiplexEntrySendReject>--

-- -------------------------------------------------------------- --
--  
-- MultiplexEntryRejectionDescriptions ::= SEQUENCEFIELD
-- {
--     multiplexTableEntryNumber   MultiplexTableEntryNumber,
--     cause       CHOICE
--     {
--         unspecifiedCause    NULL,
--         descriptorTooComplex    NULL,
--         ...
--     },
--     ...
-- }
--  
-- -------------------------------------------------------------- --

--<ASN1.Remove
--		MULTIMEDIA-SYSTEM-CONTROL.MultiplexEntryRejectionDescriptions>--

-- -------------------------------------------------------------- --
--  
-- MultiplexEntrySendRelease   ::= SEQUENCE
-- {
--     multiplexTableEntryNumber   SET SIZE (1..15) OF MultiplexTableEntryNumber,
--     ...
-- }
--  
-- -------------------------------------------------------------- --

--<ASN1.Remove
--		MULTIMEDIA-SYSTEM-CONTROL.MultiplexEntrySendRelease>--

-- -------------------------------------------------------------- --
--  
-- RequestMultiplexEntry   ::= SEQUENCE
-- {
--     entryNumbers    SET SIZE (1..15) OF MultiplexTableEntryNumber,
--     ...
-- }
--  
-- -------------------------------------------------------------- --

--<ASN1.Remove
--		MULTIMEDIA-SYSTEM-CONTROL.RequestMultiplexEntry>--

-- -------------------------------------------------------------- --
--  
-- RequestMultiplexEntryAck    ::= SEQUENCE
-- {
--     entryNumbers    SET SIZE (1..15) OF MultiplexTableEntryNumber,
--     ...
-- }
--  
-- -------------------------------------------------------------- --

--<ASN1.Remove
--		MULTIMEDIA-SYSTEM-CONTROL.RequestMultiplexEntryAck>--

-- -------------------------------------------------------------- --
--  
-- RequestMultiplexEntryReject ::= SEQUENCE
-- {
--     entryNumbers    SET SIZE (1..15) OF MultiplexTableEntryNumber,
--     rejectionDescriptions   SET SIZE (1..15) OF RequestMultiplexEntryRejectionDescriptions,
--     ...
-- }
--  
-- -------------------------------------------------------------- --

--<ASN1.Remove
--		MULTIMEDIA-SYSTEM-CONTROL.RequestMultiplexEntryReject>--

-- -------------------------------------------------------------- --
--  
-- RequestMultiplexEntryRejectionDescriptions  ::= SEQUENCE
-- {
--     multiplexTableEntryNumber   MultiplexTableEntryNumber,
--     cause       CHOICE
--     {
--         unspecifiedCause    NULL,
--         ...
--     },
--     ...
-- }
--  
-- -------------------------------------------------------------- --

--<ASN1.Remove
--		MULTIMEDIA-SYSTEM-CONTROL.RequestMultiplexEntryRejectionDescriptions>--

-- -------------------------------------------------------------- --
--  
-- RequestMultiplexEntryRelease    ::= SEQUENCE
-- {
--     entryNumbers    SET SIZE (1..15) OF MultiplexTableEntryNumber,
--  
--     ...
-- }
--  
-- -------------------------------------------------------------- --

--<ASN1.Remove
--		MULTIMEDIA-SYSTEM-CONTROL.RequestMultiplexEntryRelease>--

-- ==============================================================
-- Request mode definitions
-- ==============================================================
 
-- -------------------------------------------------------------- --
--
-- RequestMode ::= SEQUENCE
-- {
--     sequenceNumber  SequenceNumber,
--     requestedModes  SEQUENCE SIZE (1..256) OF ModeDescription,
--     ...
-- }
--  
-- -------------------------------------------------------------- --
 
--<ASN1.PDU
--		MULTIMEDIA-SYSTEM-CONTROL.RequestMode>--
--<OSS.TYPENAME
--		MULTIMEDIA-SYSTEM-CONTROL.RequestMode
--		"EmRequestMode">--
--<OSS.FIELDNAME
--		MULTIMEDIA-SYSTEM-CONTROL.RequestMode.sequenceNumber
--		"sequenceNumber">--
--<OSS.FIELDNAME
--		MULTIMEDIA-SYSTEM-CONTROL.RequestMode.requestedModes
--		"requestedModes">--

-- -------------------------------------------------------------- --
--  
-- RequestModeAck  ::= SEQUENCE
-- {
--     sequenceNumber  SequenceNumber,
--     response    CHOICE
--     {
--         willTransmitMostPreferredMode   NULL,
--         willTransmitLessPreferredMode   NULL,
--         ...
--     },
--     ...
-- }
--  
-- -------------------------------------------------------------- --
 
--<ASN1.PDU
--		MULTIMEDIA-SYSTEM-CONTROL.RequestModeAck>--
--<OSS.TYPENAME
--		MULTIMEDIA-SYSTEM-CONTROL.RequestModeAck
--		"EmRequestModeAck">--
--<OSS.FIELDNAME
--		MULTIMEDIA-SYSTEM-CONTROL.RequestModeAck.sequenceNumber
--		"sequenceNumber">--
--<OSS.ExtractType
--		MULTIMEDIA-SYSTEM-CONTROL.RequestModeAck.response>--
--<OSS.TYPENAME
--		MULTIMEDIA-SYSTEM-CONTROL.RequestModeAck.response
--		"EmRequestModeAckResponse">--
--<OSS.FIELDNAME
--		MULTIMEDIA-SYSTEM-CONTROL.RequestModeAck.response
--		"response">--
--<OSS.FIELDNAME
--		MULTIMEDIA-SYSTEM-CONTROL.RequestModeAck.response.willTransmitMostPreferredMode
--		"willTransmitMostPreferredMode">--
--<OSS.DefineName
--		MULTIMEDIA-SYSTEM-CONTROL.RequestModeAck.response.willTransmitMostPreferredMode
--		"EM_willTransmitMostPreferredMode">--
--<OSS.FIELDNAME
--		MULTIMEDIA-SYSTEM-CONTROL.RequestModeAck.response.willTransmitLessPreferredMode
--		"willTransmitLessPreferredMode">--
--<OSS.DefineName
--		MULTIMEDIA-SYSTEM-CONTROL.RequestModeAck.response.willTransmitLessPreferredMode
--		"EM_willTransmitLessPreferredMode">--

-- -------------------------------------------------------------- --
--  
-- RequestModeReject   ::= SEQUENCE
-- {
--     sequenceNumber  SequenceNumber,
--     cause       CHOICE
--     {
--         modeUnavailable         NULL,
--         multipointConstraint    NULL,
--         requestDenied           NULL,
--         ...
--     },
--     ...
-- }
--  
-- -------------------------------------------------------------- --
 
--<ASN1.PDU
--		MULTIMEDIA-SYSTEM-CONTROL.RequestModeReject>--
--<OSS.TYPENAME
--		MULTIMEDIA-SYSTEM-CONTROL.RequestModeReject
--		"EmRequestModeReject">--
--<OSS.FIELDNAME
--		MULTIMEDIA-SYSTEM-CONTROL.RequestModeReject.sequenceNumber
--		"sequenceNumber">--
--<OSS.ExtractType
--		MULTIMEDIA-SYSTEM-CONTROL.RequestModeReject.cause>--
--<OSS.TYPENAME
--		MULTIMEDIA-SYSTEM-CONTROL.RequestModeReject.cause
--		"EmRejectModeRejectCause">--
--<OSS.FIELDNAME
--		MULTIMEDIA-SYSTEM-CONTROL.RequestModeReject.cause
--		"cause">--
--<OSS.FIELDNAME
--		MULTIMEDIA-SYSTEM-CONTROL.RequestModeReject.cause.modeUnavailable
--		"modeUnavailable">--
--<OSS.DefineName
--		MULTIMEDIA-SYSTEM-CONTROL.RequestModeReject.cause.modeUnavailable
--		"EM_modeUnavailable">--
--<OSS.FIELDNAME
--		MULTIMEDIA-SYSTEM-CONTROL.RequestModeReject.cause.multipointConstraint
--		"multipointConstraint">--
--<OSS.DefineName
--		MULTIMEDIA-SYSTEM-CONTROL.RequestModeReject.cause.multipointConstraint
--		"EM_multipointConstraint">--
--<OSS.FIELDNAME
--		MULTIMEDIA-SYSTEM-CONTROL.RequestModeReject.cause.requestDenied
--		"requestDenied">--
--<OSS.DefineName
--		MULTIMEDIA-SYSTEM-CONTROL.RequestModeReject.cause.requestDenied
--		"EM_requestDenied">--

-- -------------------------------------------------------------- --
--  
-- RequestModeRelease  ::= SEQUENCE
-- {
--     ...
-- }
--
-- -------------------------------------------------------------- --

--<ASN1.PDU
--		MULTIMEDIA-SYSTEM-CONTROL.RequestModeRelease>--
--<OSS.TYPENAME
--		MULTIMEDIA-SYSTEM-CONTROL.RequestModeRelease
--		"EmRequestModeRelease">--

-- ==============================================================
-- Request mode definitions: Mode description
-- ==============================================================

-- -------------------------------------------------------------- --
--
-- ModeDescription ::= SET SIZE (1..256) OF ModeElement
--
-- -------------------------------------------------------------- --
 
--<ASN1.PDU
--		MULTIMEDIA-SYSTEM-CONTROL.ModeDescription>--
--<OSS.TYPENAME
--		MULTIMEDIA-SYSTEM-CONTROL.ModeDescription
--		"EmModeDescription">--

-- -------------------------------------------------------------- --
--
-- ModeElement ::= SEQUENCE
-- {
--     type        CHOICE
--     {
--         nonStandard NonStandardParameter,
--         videoMode   VideoMode,
--         audioMode   AudioMode,
--         dataMode    DataMode,
--         encryptionMode  EncryptionMode,
--         ...,
--         h235Mode        H235Mode
--     },
--  
--     h223ModeParameters  H223ModeParameters  OPTIONAL,
--     ...,
--     v76ModeParameters   V76ModeParameters  OPTIONAL,
--     h2250ModeParameters H2250ModeParameters OPTIONAL
--  
-- }
--
-- -------------------------------------------------------------- --
 
--<ASN1.PDU
--		MULTIMEDIA-SYSTEM-CONTROL.ModeElement>--
--<OSS.TYPENAME
--		MULTIMEDIA-SYSTEM-CONTROL.ModeElement
--		"EmModeElement">--
--<OSS.ExtractType
--		MULTIMEDIA-SYSTEM-CONTROL.ModeElement.type>--
--<OSS.TYPENAME
--		MULTIMEDIA-SYSTEM-CONTROL.ModeElement.type
--		"EmModeElementType">--
--<OSS.FIELDNAME
--		MULTIMEDIA-SYSTEM-CONTROL.ModeElement.type
--		"type">--
--<OSS.FIELDNAME
--		MULTIMEDIA-SYSTEM-CONTROL.ModeElement.type.nonStandard
--		"nonStandard">--
--<OSS.DefineName
--		MULTIMEDIA-SYSTEM-CONTROL.ModeElement.type.nonStandard
--		"EM_ModeElementType_nonStandard">--
--<OSS.FIELDNAME
--		MULTIMEDIA-SYSTEM-CONTROL.ModeElement.type.videoMode
--		"videoMode">--
--<OSS.DefineName
--		MULTIMEDIA-SYSTEM-CONTROL.ModeElement.type.videoMode
--		"EM_ModeElementType_videoMode">--
--<OSS.FIELDNAME
--		MULTIMEDIA-SYSTEM-CONTROL.ModeElement.type.audioMode
--		"audioMode">--
--<OSS.DefineName
--		MULTIMEDIA-SYSTEM-CONTROL.ModeElement.type.audioMode
--		"EM_ModeElementType_audioMode">--
--<OSS.FIELDNAME
--		MULTIMEDIA-SYSTEM-CONTROL.ModeElement.type.dataMode
--		"dataMode">--
--<OSS.DefineName
--		MULTIMEDIA-SYSTEM-CONTROL.ModeElement.type.dataMode
--		"EM_ModeElementType_dataMode">--
--<OSS.FIELDNAME
--		MULTIMEDIA-SYSTEM-CONTROL.ModeElement.type.encryptionMode
--		"encryptionMode">--
--<OSS.DefineName
--		MULTIMEDIA-SYSTEM-CONTROL.ModeElement.type.encryptionMode
--		"EM_encryptionMode">--
--<OSS.FIELDNAME
--		MULTIMEDIA-SYSTEM-CONTROL.ModeElement.type.h235Mode
--		"h235Mode">--
--<OSS.DefineName
--		MULTIMEDIA-SYSTEM-CONTROL.ModeElement.type.h235Mode
--		"EM_h235Mode">--
--<ASN1.Remove
--		MULTIMEDIA-SYSTEM-CONTROL.ModeElement.h223ModeParameters>--
--<ASN1.Remove
--		MULTIMEDIA-SYSTEM-CONTROL.ModeElement.v76ModeParameters>--
--<OSS.FIELDNAME
--		MULTIMEDIA-SYSTEM-CONTROL.ModeElement.h2250ModeParameters
--		"h2250ModeParameters">--
--<OSS.DefineName
--		MULTIMEDIA-SYSTEM-CONTROL.ModeElement.h2250ModeParameters
--		"EM_h2250ModeParameters">--

-- -------------------------------------------------------------- --
--
-- H235Mode ::= SEQUENCE
-- {
--     encryptionAuthenticationAndIntegrity    EncryptionAuthenticationAndIntegrity,
--  
--     mediaMode   CHOICE
--     {
--         nonStandard NonStandardParameter,
--         videoMode   VideoMode,
--         audioMode   AudioMode,
--         dataMode    DataMode,
--         ...
--     },
--     ...
-- }
--
-- -------------------------------------------------------------- --

--<ASN1.PDU
--		MULTIMEDIA-SYSTEM-CONTROL.H235Mode>--
--<OSS.TYPENAME
--		MULTIMEDIA-SYSTEM-CONTROL.H235Mode
--		"EmH235Mode">--
--<OSS.FIELDNAME
--		MULTIMEDIA-SYSTEM-CONTROL.H235Mode.encryptionAuthenticationAndIntegrity
--		"encryptionAuthenticationAndIntegrity">--
--<OSS.ExtractType
--		MULTIMEDIA-SYSTEM-CONTROL.H235Mode.mediaMode>--
--<OSS.TYPENAME
--		MULTIMEDIA-SYSTEM-CONTROL.H235Mode.mediaMode
--		"EmH235MediaMode">--
--<OSS.FIELDNAME
--		MULTIMEDIA-SYSTEM-CONTROL.H235Mode.mediaMode
--		"mediaMode">--
--<OSS.FIELDNAME
--		MULTIMEDIA-SYSTEM-CONTROL.H235Mode.mediaMode.nonStandard
--		"nonStandard">--
--<OSS.DefineName
--		MULTIMEDIA-SYSTEM-CONTROL.H235Mode.mediaMode.nonStandard
--		"EM_H235MediaMode_nonStandard">--
--<OSS.FIELDNAME
--		MULTIMEDIA-SYSTEM-CONTROL.H235Mode.mediaMode.videoMode
--		"videoMode">--
--<OSS.DefineName
--		MULTIMEDIA-SYSTEM-CONTROL.H235Mode.mediaMode.videoMode
--		"EM_H235MediaMode_videoMode">--
--<OSS.FIELDNAME
--		MULTIMEDIA-SYSTEM-CONTROL.H235Mode.mediaMode.audioMode
--		"audioMode">--
--<OSS.DefineName
--		MULTIMEDIA-SYSTEM-CONTROL.H235Mode.mediaMode.audioMode
--		"EM_H235MediaMode_audioMode">--
--<OSS.FIELDNAME
--		MULTIMEDIA-SYSTEM-CONTROL.H235Mode.mediaMode.dataMode
--		"dataMode">--
--<OSS.DefineName
--		MULTIMEDIA-SYSTEM-CONTROL.H235Mode.mediaMode.dataMode
--		"EM_H235MediaMode_dataMode">--

-- -------------------------------------------------------------- --
--
-- H223ModeParameters  ::= SEQUENCE
-- {
--     adaptationLayerType CHOICE
--     {
--         nonStandard     NonStandardParameter,
--         al1Framed                   NULL,
--         al1NotFramed                NULL,
--         al2WithoutSequenceNumbers   NULL,
--         al2WithSequenceNumbers      NULL,
--         al3     SEQUENCE
--         {
--             controlFieldOctets  INTEGER(0..2),
--             sendBufferSize      INTEGER(0..16777215)
--         },
--         ...,
--         al1M    H223AL1MParameters,
--         al2M    H223AL2MParameters,
--         al3M    H223AL3MParameters
--     },
--  
--     segmentableFlag BOOLEAN,
--     ...
-- }
--
-- -------------------------------------------------------------- --
 
--<ASN1.Remove
--		MULTIMEDIA-SYSTEM-CONTROL.H223ModeParameters>--

-- -------------------------------------------------------------- --
--  
-- V76ModeParameters   ::= CHOICE
-- {
--     suspendResumewAddress   NULL,
--     suspendResumewoAddress  NULL,
--     ...
-- }
--
-- -------------------------------------------------------------- --

--<ASN1.Remove
--		MULTIMEDIA-SYSTEM-CONTROL.V76ModeParameters>--

-- -------------------------------------------------------------- --
--
-- H2250ModeParameters ::= SEQUENCE
-- {
--     redundancyEncodingMode  RedundancyEncodingMode OPTIONAL,
--     ...
-- }
--  
-- -------------------------------------------------------------- --

--<OSS.TYPENAME
--		MULTIMEDIA-SYSTEM-CONTROL.H2250ModeParameters
--		"EmH2250ModeParameters">--
--<OSS.FIELDNAME
--		MULTIMEDIA-SYSTEM-CONTROL.H2250ModeParameters.redundancyEncodingMode
--		"redundancyEncodingMode">--
--<OSS.DefineName
--		MULTIMEDIA-SYSTEM-CONTROL.H2250ModeParameters.redundancyEncodingMode
--		"EM_redundancyEncodingMode">--

-- -------------------------------------------------------------- --
--  
-- RedundancyEncodingMode ::= SEQUENCE
-- {
--     redundancyEncodingMethod    RedundancyEncodingMethod,
--     secondaryEncoding   CHOICE
--     {
--         nonStandard NonStandardParameter,
--         audioData   AudioMode,
--         ...
--     } OPTIONAL,
--     ...
-- }
--
-- -------------------------------------------------------------- --

--<ASN1.PDU
--		MULTIMEDIA-SYSTEM-CONTROL.RedundancyEncodingMode>--
--<OSS.TYPENAME
--		MULTIMEDIA-SYSTEM-CONTROL.RedundancyEncodingMode
--		"EmRedundancyEncodingMode">--
--<OSS.FIELDNAME
--		MULTIMEDIA-SYSTEM-CONTROL.RedundancyEncodingMode.redundancyEncodingMethod
--		"redundancyEncodingMethod">--
--<OSS.ExtractType
--		MULTIMEDIA-SYSTEM-CONTROL.RedundancyEncodingMode.secondaryEncoding>--
--<OSS.TYPENAME
--		MULTIMEDIA-SYSTEM-CONTROL.RedundancyEncodingMode.secondaryEncoding
--		"EmSecondaryEncoding">--
--<OSS.FIELDNAME
--		MULTIMEDIA-SYSTEM-CONTROL.RedundancyEncodingMode.secondaryEncoding
--		"secondaryEncoding">--
--<OSS.DefineName
--		MULTIMEDIA-SYSTEM-CONTROL.RedundancyEncodingMode.secondaryEncoding
--		"EM_RedundancyEncodingMode_secondaryEncoding">--
--<OSS.FIELDNAME
--		MULTIMEDIA-SYSTEM-CONTROL.RedundancyEncodingMode.secondaryEncoding.nonStandard
--		"nonStandard">--
--<OSS.DefineName
--		MULTIMEDIA-SYSTEM-CONTROL.RedundancyEncodingMode.secondaryEncoding.nonStandard
--		"EM_SecondaryEncoding_nonStandard">--
--<OSS.FIELDNAME
--		MULTIMEDIA-SYSTEM-CONTROL.RedundancyEncodingMode.secondaryEncoding.audioData
--		"audioData">--
--<OSS.DefineName
--		MULTIMEDIA-SYSTEM-CONTROL.RedundancyEncodingMode.secondaryEncoding.audioData
--		"EM_SecondaryEncoding_audioData">--

-- ==============================================================
-- Request mode definitions: Video modes
-- ==============================================================
 
-- -------------------------------------------------------------- --
--
-- VideoMode       ::= CHOICE
-- {
--     nonStandard         NonStandardParameter,
--     h261VideoMode       H261VideoMode,
--     h262VideoMode       H262VideoMode,
--     h263VideoMode       H263VideoMode,
--     is11172VideoMode    IS11172VideoMode,
--     ...
-- }
--
-- -------------------------------------------------------------- --
 
--<ASN1.PDU
--		MULTIMEDIA-SYSTEM-CONTROL.VideoMode>--
--<OSS.TYPENAME
--		MULTIMEDIA-SYSTEM-CONTROL.VideoMode
--		"EmVideoMode">--
--<OSS.FIELDNAME
--		MULTIMEDIA-SYSTEM-CONTROL.VideoMode.nonStandard
--		"nonStandard">--
--<OSS.DefineName
--		MULTIMEDIA-SYSTEM-CONTROL.VideoMode.nonStandard
--		"EM_VideoMode_nonStandard">--
--<OSS.FIELDNAME
--		MULTIMEDIA-SYSTEM-CONTROL.VideoMode.h261VideoMode
--		"h261VideoMode">--
--<OSS.DefineName
--		MULTIMEDIA-SYSTEM-CONTROL.VideoMode.h261VideoMode
--		"EM_h261VideoMode">--
--<OSS.FIELDNAME
--		MULTIMEDIA-SYSTEM-CONTROL.VideoMode.h262VideoMode
--		"h262VideoMode">--
--<OSS.DefineName
--		MULTIMEDIA-SYSTEM-CONTROL.VideoMode.h262VideoMode
--		"EM_h262VideoMode">--
--<OSS.FIELDNAME
--		MULTIMEDIA-SYSTEM-CONTROL.VideoMode.h263VideoMode
--		"h263VideoMode">--
--<OSS.DefineName
--		MULTIMEDIA-SYSTEM-CONTROL.VideoMode.h263VideoMode
--		"EM_h263VideoMode">--
--<OSS.FIELDNAME
--		MULTIMEDIA-SYSTEM-CONTROL.VideoMode.is11172VideoMode
--		"is11172VideoMode">--
--<OSS.DefineName
--		MULTIMEDIA-SYSTEM-CONTROL.VideoMode.is11172VideoMode
--		"EM_is11172VideoMode">--

-- -------------------------------------------------------------- --
--
-- H261VideoMode   ::= SEQUENCE
-- {
--     resolution  CHOICE
--     {
--         qcif    NULL,
--         cif     NULL
--     },
--     bitRate                 INTEGER (1..19200),
--     stillImageTransmission  BOOLEAN,
--     ...
-- }
--
-- -------------------------------------------------------------- --
 
--<ASN1.PDU
--		MULTIMEDIA-SYSTEM-CONTROL.H261VideoMode>--
--<OSS.TYPENAME
--		MULTIMEDIA-SYSTEM-CONTROL.H261VideoMode
--		"EmH261VideoMode">--
--<OSS.ExtractType
--		MULTIMEDIA-SYSTEM-CONTROL.H261VideoMode.resolution>--
--<OSS.TYPENAME
--		MULTIMEDIA-SYSTEM-CONTROL.H261VideoMode.resolution
--		"EmH261VideoModeResolution">--
--<OSS.FIELDNAME
--		MULTIMEDIA-SYSTEM-CONTROL.H261VideoMode.resolution
--		"resolution">--
--<OSS.FIELDNAME
--		MULTIMEDIA-SYSTEM-CONTROL.H261VideoMode.resolution.qcif
--		"qcif">--
--<OSS.DefineName
--		MULTIMEDIA-SYSTEM-CONTROL.H261VideoMode.resolution.qcif
--		"EM_H261VideoModeResolution_qcif">--
--<OSS.FIELDNAME
--		MULTIMEDIA-SYSTEM-CONTROL.H261VideoMode.resolution.cif
--		"cif">--
--<OSS.DefineName
--		MULTIMEDIA-SYSTEM-CONTROL.H261VideoMode.resolution.cif
--		"EM_H261VideoModeResolution_cif">--
--<OSS.FIELDNAME
--		MULTIMEDIA-SYSTEM-CONTROL.H261VideoMode.bitRate
--		"bitRate">--
--<OSS.FIELDNAME
--		MULTIMEDIA-SYSTEM-CONTROL.H261VideoMode.stillImageTransmission
--		"stillImageTransmission">--

-- -------------------------------------------------------------- --
--
-- H262VideoMode   ::= SEQUENCE
-- {
--     profileAndLevel CHOICE
--     {
--         profileAndLevel-SPatML          NULL,
--         profileAndLevel-MPatLL          NULL,
--         profileAndLevel-MPatML          NULL,
--         profileAndLevel-MPatH-14        NULL,
--         profileAndLevel-MPatHL          NULL,
--         profileAndLevel-SNRatLL         NULL,
--         profileAndLevel-SNRatML         NULL,
--         profileAndLevel-SpatialatH-14   NULL,
--         profileAndLevel-HPatML          NULL,
--         profileAndLevel-HPatH-14        NULL,
--         profileAndLevel-HPatHL          NULL,
--         ...
--     },
--     videoBitRate    INTEGER(0..1073741823)  OPTIONAL,
--     vbvBufferSize   INTEGER(0..262143)  OPTIONAL,
--     samplesPerLine  INTEGER(0..16383)  OPTIONAL,
--     linesPerFrame   INTEGER(0..16383)  OPTIONAL,
--     framesPerSecond INTEGER(0..15)  OPTIONAL,
--     luminanceSampleRate INTEGER(0..4294967295)  OPTIONAL,
--     ...
-- }
--
-- -------------------------------------------------------------- --

--<ASN1.PDU
--		MULTIMEDIA-SYSTEM-CONTROL.H262VideoMode>--
--<OSS.TYPENAME
--		MULTIMEDIA-SYSTEM-CONTROL.H262VideoMode
--		"EmH262VideoMode">--
--<OSS.ExtractType
--		MULTIMEDIA-SYSTEM-CONTROL.H262VideoMode.profileAndLevel>--
--<OSS.TYPENAME
--		MULTIMEDIA-SYSTEM-CONTROL.H262VideoMode.profileAndLevel
--		"EmH262VideoModeProfileAndLevel">--
--<OSS.FIELDNAME
--		MULTIMEDIA-SYSTEM-CONTROL.H262VideoMode.profileAndLevel
--		"profileAndLevel">--
--<OSS.FIELDNAME
--		MULTIMEDIA-SYSTEM-CONTROL.H262VideoMode.profileAndLevel.profileAndLevel-SPatML
--		"profileAndLevel_SPatML">--
--<OSS.DefineName
--		MULTIMEDIA-SYSTEM-CONTROL.H262VideoMode.profileAndLevel.profileAndLevel-SPatML
--		"EM_profileAndLevel_SPatML">--
--<OSS.FIELDNAME
--		MULTIMEDIA-SYSTEM-CONTROL.H262VideoMode.profileAndLevel.profileAndLevel-MPatLL
--		"profileAndLevel_MPatLL">--
--<OSS.DefineName
--		MULTIMEDIA-SYSTEM-CONTROL.H262VideoMode.profileAndLevel.profileAndLevel-MPatLL
--		"EM_profileAndLevel_MPatLL">--
--<OSS.FIELDNAME
--		MULTIMEDIA-SYSTEM-CONTROL.H262VideoMode.profileAndLevel.profileAndLevel-MPatML
--		"profileAndLevel_MPatML">--
--<OSS.DefineName
--		MULTIMEDIA-SYSTEM-CONTROL.H262VideoMode.profileAndLevel.profileAndLevel-MPatML
--		"EM_profileAndLevel_MPatML">--
--<OSS.FIELDNAME
--		MULTIMEDIA-SYSTEM-CONTROL.H262VideoMode.profileAndLevel.profileAndLevel-MPatH-14
--		"profileAndLevel_MPatH_14">--
--<OSS.DefineName
--		MULTIMEDIA-SYSTEM-CONTROL.H262VideoMode.profileAndLevel.profileAndLevel-MPatH-14
--		"EM_profileAndLevel_MPatH_14">--
--<OSS.FIELDNAME
--		MULTIMEDIA-SYSTEM-CONTROL.H262VideoMode.profileAndLevel.profileAndLevel-MPatHL
--		"profileAndLevel_MPatHL">--
--<OSS.DefineName
--		MULTIMEDIA-SYSTEM-CONTROL.H262VideoMode.profileAndLevel.profileAndLevel-MPatHL
--		"EM_profileAndLevel_MPatHL">--
--<OSS.FIELDNAME
--		MULTIMEDIA-SYSTEM-CONTROL.H262VideoMode.profileAndLevel.profileAndLevel-SNRatLL
--		"profileAndLevel_SNRatLL">--
--<OSS.DefineName
--		MULTIMEDIA-SYSTEM-CONTROL.H262VideoMode.profileAndLevel.profileAndLevel-SNRatLL
--		"EM_profileAndLevel_SNRatLL">--
--<OSS.FIELDNAME
--		MULTIMEDIA-SYSTEM-CONTROL.H262VideoMode.profileAndLevel.profileAndLevel-SNRatML
--		"profileAndLevel_SNRatML">--
--<OSS.DefineName
--		MULTIMEDIA-SYSTEM-CONTROL.H262VideoMode.profileAndLevel.profileAndLevel-SNRatML
--		"EM_profileAndLevel_SNRatML">--
--<OSS.FIELDNAME
--		MULTIMEDIA-SYSTEM-CONTROL.H262VideoMode.profileAndLevel.profileAndLevel-SpatialatH-14
--		"profileAndLevel_SpatialatH_14">--
--<OSS.DefineName
--		MULTIMEDIA-SYSTEM-CONTROL.H262VideoMode.profileAndLevel.profileAndLevel-SpatialatH-14
--		"EM_profileAndLevel_SpatialatH_14">--
--<OSS.FIELDNAME
--		MULTIMEDIA-SYSTEM-CONTROL.H262VideoMode.profileAndLevel.profileAndLevel-HPatML
--		"profileAndLevel_HPatML">--
--<OSS.DefineName
--		MULTIMEDIA-SYSTEM-CONTROL.H262VideoMode.profileAndLevel.profileAndLevel-HPatML
--		"EM_profileAndLevel_HPatML">--
--<OSS.FIELDNAME
--		MULTIMEDIA-SYSTEM-CONTROL.H262VideoMode.profileAndLevel.profileAndLevel-HPatH-14
--		"profileAndLevel_HPatH_14">--
--<OSS.DefineName
--		MULTIMEDIA-SYSTEM-CONTROL.H262VideoMode.profileAndLevel.profileAndLevel-HPatH-14
--		"EM_profileAndLevel_HPatH_14">--
--<OSS.FIELDNAME
--		MULTIMEDIA-SYSTEM-CONTROL.H262VideoMode.profileAndLevel.profileAndLevel-HPatHL
--		"profileAndLevel_HPatHL">--
--<OSS.DefineName
--		MULTIMEDIA-SYSTEM-CONTROL.H262VideoMode.profileAndLevel.profileAndLevel-HPatHL
--		"EM_profileAndLevel_HPatHL">--
--<OSS.FIELDNAME
--		MULTIMEDIA-SYSTEM-CONTROL.H262VideoMode.videoBitRate
--		"videoBitRate">--
--<OSS.DefineName
--		MULTIMEDIA-SYSTEM-CONTROL.H262VideoMode.videoBitRate
--		"EM_H262VideoMode_videoBitRate">--
--<OSS.FIELDNAME
--		MULTIMEDIA-SYSTEM-CONTROL.H262VideoMode.vbvBufferSize
--		"vbvBufferSize">--
--<OSS.DefineName
--		MULTIMEDIA-SYSTEM-CONTROL.H262VideoMode.vbvBufferSize
--		"EM_H262VideoMode_vbvBufferSize">--
--<OSS.FIELDNAME
--		MULTIMEDIA-SYSTEM-CONTROL.H262VideoMode.samplesPerLine
--		"samplesPerLine">--
--<OSS.DefineName
--		MULTIMEDIA-SYSTEM-CONTROL.H262VideoMode.samplesPerLine
--		"EM_H262VideoMode_samplesPerLine">--
--<OSS.FIELDNAME
--		MULTIMEDIA-SYSTEM-CONTROL.H262VideoMode.linesPerFrame
--		"linesPerFrame">--
--<OSS.DefineName
--		MULTIMEDIA-SYSTEM-CONTROL.H262VideoMode.linesPerFrame
--		"EM_H262VideoMode_linesPerFrame">--
--<OSS.FIELDNAME
--		MULTIMEDIA-SYSTEM-CONTROL.H262VideoMode.framesPerSecond
--		"framesPerSecond">--
--<OSS.DefineName
--		MULTIMEDIA-SYSTEM-CONTROL.H262VideoMode.framesPerSecond
--		"EM_H262VideoMode_framesPerSecond">--
--<OSS.FIELDNAME
--		MULTIMEDIA-SYSTEM-CONTROL.H262VideoMode.luminanceSampleRate
--		"luminanceSampleRate">--
--<OSS.DefineName
--		MULTIMEDIA-SYSTEM-CONTROL.H262VideoMode.luminanceSampleRate
--		"EM_H262VideoMode_luminanceSampleRate">--

-- -------------------------------------------------------------- --
--
-- H263VideoMode   ::= SEQUENCE
-- {
--     resolution  CHOICE
--     {
--         sqcif   NULL,
--         qcif    NULL,
--         cif     NULL,
--         cif4    NULL,
--         cif16   NULL,
--         ...
--     },
--     bitRate             INTEGER (1..19200),
--     unrestrictedVector  BOOLEAN,
--     arithmeticCoding    BOOLEAN,
--     advancedPrediction  BOOLEAN,
--     pbFrames            BOOLEAN,
--     ...,
--  
--     errorCompensation   BOOLEAN,
--     enhancementLayerInfo    EnhancementLayerInfo OPTIONAL,
--     h263Options         H263Options OPTIONAL
--  
-- }
--
-- -------------------------------------------------------------- --

--<ASN1.PDU
--		MULTIMEDIA-SYSTEM-CONTROL.H263VideoMode>--
--<OSS.TYPENAME
--		MULTIMEDIA-SYSTEM-CONTROL.H263VideoMode
--		"EmH263VideoMode">--
--<OSS.ExtractType
--		MULTIMEDIA-SYSTEM-CONTROL.H263VideoMode.resolution>--
--<OSS.TYPENAME
--		MULTIMEDIA-SYSTEM-CONTROL.H263VideoMode.resolution
--		"EmH263VideoModeResolution">--
--<OSS.FIELDNAME
--		MULTIMEDIA-SYSTEM-CONTROL.H263VideoMode.resolution
--		"resolution">--
--<OSS.FIELDNAME
--		MULTIMEDIA-SYSTEM-CONTROL.H263VideoMode.resolution.sqcif
--		"sqcif">--
--<OSS.DefineName
--		MULTIMEDIA-SYSTEM-CONTROL.H263VideoMode.resolution.sqcif
--		"EM_sqcif">--
--<OSS.FIELDNAME
--		MULTIMEDIA-SYSTEM-CONTROL.H263VideoMode.resolution.qcif
--		"qcif">--
--<OSS.DefineName
--		MULTIMEDIA-SYSTEM-CONTROL.H263VideoMode.resolution.qcif
--		"EM_H263VideoModeResolution_qcif">--
--<OSS.FIELDNAME
--		MULTIMEDIA-SYSTEM-CONTROL.H263VideoMode.resolution.cif
--		"cif">--
--<OSS.DefineName
--		MULTIMEDIA-SYSTEM-CONTROL.H263VideoMode.resolution.cif
--		"EM_H263VideoModeResolution_cif">--
--<OSS.FIELDNAME
--		MULTIMEDIA-SYSTEM-CONTROL.H263VideoMode.resolution.cif4
--		"cif4">--
--<OSS.DefineName
--		MULTIMEDIA-SYSTEM-CONTROL.H263VideoMode.resolution.cif4
--		"EM_cif4">--
--<OSS.FIELDNAME
--		MULTIMEDIA-SYSTEM-CONTROL.H263VideoMode.resolution.cif16
--		"cif16">--
--<OSS.DefineName
--		MULTIMEDIA-SYSTEM-CONTROL.H263VideoMode.resolution.cif16
--		"EM_cif16">--
--<OSS.FIELDNAME
--		MULTIMEDIA-SYSTEM-CONTROL.H263VideoMode.bitRate
--		"bitRate">--
--<OSS.FIELDNAME
--		MULTIMEDIA-SYSTEM-CONTROL.H263VideoMode.unrestrictedVector
--		"unrestrictedVector">--
--<OSS.FIELDNAME
--		MULTIMEDIA-SYSTEM-CONTROL.H263VideoMode.arithmeticCoding
--		"arithmeticCoding">--
--<OSS.FIELDNAME
--		MULTIMEDIA-SYSTEM-CONTROL.H263VideoMode.advancedPrediction
--		"advancedPrediction">--
--<OSS.FIELDNAME
--		MULTIMEDIA-SYSTEM-CONTROL.H263VideoMode.pbFrames
--		"pbFrames">--
--<OSS.FIELDNAME
--		MULTIMEDIA-SYSTEM-CONTROL.H263VideoMode.errorCompensation
--		"errorCompensation">--
--<OSS.DefineName
--		MULTIMEDIA-SYSTEM-CONTROL.H263VideoMode.errorCompensation
--		"EM_H263VideoMode_errorCompensation">--
--<OSS.FIELDNAME
--		MULTIMEDIA-SYSTEM-CONTROL.H263VideoMode.enhancementLayerInfo
--		"enhancementLayerInfo">--
--<OSS.DefineName
--		MULTIMEDIA-SYSTEM-CONTROL.H263VideoMode.enhancementLayerInfo
--		"EM_H263VideoMode_enhancementLayerInfo">--
--<OSS.FIELDNAME
--		MULTIMEDIA-SYSTEM-CONTROL.H263VideoMode.h263Options
--		"h263Options">--
--<OSS.DefineName
--		MULTIMEDIA-SYSTEM-CONTROL.H263VideoMode.h263Options
--		"EM_H263VideoMode_h263Options">--

-- -------------------------------------------------------------- --
--
-- IS11172VideoMode    ::= SEQUENCE
-- {
--     constrainedBitstream    BOOLEAN,
--     videoBitRate            INTEGER(0..1073741823) OPTIONAL,
--     vbvBufferSize           INTEGER(0..262143) OPTIONAL,
--     samplesPerLine          INTEGER(0..16383) OPTIONAL,
--     linesPerFrame           INTEGER(0..16383) OPTIONAL,
--     pictureRate             INTEGER(0..15) OPTIONAL,
--     luminanceSampleRate     INTEGER(0..4294967295) OPTIONAL,
--     ...
-- }
--
-- -------------------------------------------------------------- --
 
--<ASN1.PDU
--		MULTIMEDIA-SYSTEM-CONTROL.IS11172VideoMode>--
--<OSS.TYPENAME
--		MULTIMEDIA-SYSTEM-CONTROL.IS11172VideoMode
--		"EmIS11172VideoMode">--
--<OSS.FIELDNAME
--		MULTIMEDIA-SYSTEM-CONTROL.IS11172VideoMode.constrainedBitstream
--		"constrainedBitstream">--
--<OSS.FIELDNAME
--		MULTIMEDIA-SYSTEM-CONTROL.IS11172VideoMode.videoBitRate
--		"videoBitRate">--
--<OSS.DefineName
--		MULTIMEDIA-SYSTEM-CONTROL.IS11172VideoMode.videoBitRate
--		"EM_IS11172VideoMode_videoBitRate">--
--<OSS.FIELDNAME
--		MULTIMEDIA-SYSTEM-CONTROL.IS11172VideoMode.vbvBufferSize
--		"vbvBufferSize">--
--<OSS.DefineName
--		MULTIMEDIA-SYSTEM-CONTROL.IS11172VideoMode.vbvBufferSize
--		"EM_IS11172VideoMode_vbvBufferSize">--
--<OSS.FIELDNAME
--		MULTIMEDIA-SYSTEM-CONTROL.IS11172VideoMode.samplesPerLine
--		"samplesPerLine">--
--<OSS.DefineName
--		MULTIMEDIA-SYSTEM-CONTROL.IS11172VideoMode.samplesPerLine
--		"EM_IS11172VideoMode_samplesPerLine">--
--<OSS.FIELDNAME
--		MULTIMEDIA-SYSTEM-CONTROL.IS11172VideoMode.linesPerFrame
--		"linesPerFrame">--
--<OSS.DefineName
--		MULTIMEDIA-SYSTEM-CONTROL.IS11172VideoMode.linesPerFrame
--		"EM_IS11172VideoMode_linesPerFrame">--
--<OSS.FIELDNAME
--		MULTIMEDIA-SYSTEM-CONTROL.IS11172VideoMode.pictureRate
--		"pictureRate">--
--<OSS.DefineName
--		MULTIMEDIA-SYSTEM-CONTROL.IS11172VideoMode.pictureRate
--		"EM_IS11172VideoMode_pictureRate">--
--<OSS.FIELDNAME
--		MULTIMEDIA-SYSTEM-CONTROL.IS11172VideoMode.luminanceSampleRate
--		"luminanceSampleRate">--
--<OSS.DefineName
--		MULTIMEDIA-SYSTEM-CONTROL.IS11172VideoMode.luminanceSampleRate
--		"EM_IS11172VideoMode_luminanceSampleRate">--

-- ==============================================================
-- Request mode definitions: Audio modes
-- ==============================================================
 
-- -------------------------------------------------------------- --
--
-- AudioMode   ::= CHOICE
-- {
--     nonStandard NonStandardParameter,
--     g711Alaw64k NULL,
--     g711Alaw56k NULL,
--     g711Ulaw64k NULL,
--     g711Ulaw56k NULL,
--  
--     g722-64k    NULL,
--     g722-56k    NULL,
--     g722-48k    NULL,
--  
--     g728        NULL,
--     g729        NULL,
--     g729AnnexA  NULL,
--  
--     g7231       CHOICE
--     {
--         noSilenceSuppressionLowRate     NULL,
--         noSilenceSuppressionHighRate    NULL,
--         silenceSuppressionLowRate       NULL,
--         silenceSuppressionHighRate      NULL
--     },
--  
--     is11172AudioMode    IS11172AudioMode,
--     is13818AudioMode    IS13818AudioMode,
--  
--     ...,
--     g729wAnnexB         INTEGER(1..256),
--     g729AnnexAwAnnexB   INTEGER(1..256),
--     g7231AnnexCMode     G7231AnnexCMode,
--     gsmFullRate         GSMAudioCapability,
--     gsmHalfRate         GSMAudioCapability,
--     gsmEnhancedFullRate GSMAudioCapability
-- 
-- }
--
-- -------------------------------------------------------------- --
 
--<ASN1.PDU
--		MULTIMEDIA-SYSTEM-CONTROL.AudioMode>--
--<OSS.TYPENAME
--		MULTIMEDIA-SYSTEM-CONTROL.AudioMode
--		"EmAudioMode">--
--<OSS.FIELDNAME
--		MULTIMEDIA-SYSTEM-CONTROL.AudioMode.nonStandard
--		"nonStandard">--
--<OSS.DefineName
--		MULTIMEDIA-SYSTEM-CONTROL.AudioMode.nonStandard
--		"EM_AudioMode_nonStandard">--
--<OSS.FIELDNAME
--		MULTIMEDIA-SYSTEM-CONTROL.AudioMode.g711Alaw64k
--		"g711Alaw64k">--
--<OSS.DefineName
--		MULTIMEDIA-SYSTEM-CONTROL.AudioMode.g711Alaw64k
--		"EM_AudioMode_g711Alaw64k">--
--<OSS.FIELDNAME
--		MULTIMEDIA-SYSTEM-CONTROL.AudioMode.g711Alaw56k
--		"g711Alaw56k">--
--<OSS.DefineName
--		MULTIMEDIA-SYSTEM-CONTROL.AudioMode.g711Alaw56k
--		"EM_AudioMode_g711Alaw56k">--
--<OSS.FIELDNAME
--		MULTIMEDIA-SYSTEM-CONTROL.AudioMode.g711Ulaw64k
--		"g711Ulaw64k">--
--<OSS.DefineName
--		MULTIMEDIA-SYSTEM-CONTROL.AudioMode.g711Ulaw64k
--		"EM_AudioMode_g711Ulaw64k">--
--<OSS.FIELDNAME
--		MULTIMEDIA-SYSTEM-CONTROL.AudioMode.g711Ulaw56k
--		"g711Ulaw56k">--
--<OSS.DefineName
--		MULTIMEDIA-SYSTEM-CONTROL.AudioMode.g711Ulaw56k
--		"EM_AudioMode_g711Ulaw56k">--
--<OSS.FIELDNAME
--		MULTIMEDIA-SYSTEM-CONTROL.AudioMode.g722-64k
--		"g722_64k">--
--<OSS.DefineName
--		MULTIMEDIA-SYSTEM-CONTROL.AudioMode.g722-64k
--		"EM_AudioMode_g722_64k">--
--<OSS.FIELDNAME
--		MULTIMEDIA-SYSTEM-CONTROL.AudioMode.g722-56k
--		"g722_56k">--
--<OSS.DefineName
--		MULTIMEDIA-SYSTEM-CONTROL.AudioMode.g722-56k
--		"EM_AudioMode_g722_56k">--
--<OSS.FIELDNAME
--		MULTIMEDIA-SYSTEM-CONTROL.AudioMode.g722-48k
--		"g722_48k">--
--<OSS.DefineName
--		MULTIMEDIA-SYSTEM-CONTROL.AudioMode.g722-48k
--		"EM_AudioMode_g722_48k">--
--<OSS.FIELDNAME
--		MULTIMEDIA-SYSTEM-CONTROL.AudioMode.g728
--		"g728">--
--<OSS.DefineName
--		MULTIMEDIA-SYSTEM-CONTROL.AudioMode.g728
--		"EM_AudioMode_g728">--
--<OSS.FIELDNAME
--		MULTIMEDIA-SYSTEM-CONTROL.AudioMode.g729
--		"g729">--
--<OSS.DefineName
--		MULTIMEDIA-SYSTEM-CONTROL.AudioMode.g729
--		"EM_AudioMode_g729">--
--<OSS.FIELDNAME
--		MULTIMEDIA-SYSTEM-CONTROL.AudioMode.g729AnnexA
--		"g729AnnexA">--
--<OSS.DefineName
--		MULTIMEDIA-SYSTEM-CONTROL.AudioMode.g729AnnexA
--		"EM_AudioMode_g729AnnexA">--
--<OSS.ExtractType
--		MULTIMEDIA-SYSTEM-CONTROL.AudioMode.g7231>--
--<OSS.TYPENAME
--		MULTIMEDIA-SYSTEM-CONTROL.AudioMode.g7231
--		"EmAudioModeG7231">--
--<OSS.FIELDNAME
--		MULTIMEDIA-SYSTEM-CONTROL.AudioMode.g7231
--		"g7231">--
--<OSS.DefineName
--		MULTIMEDIA-SYSTEM-CONTROL.AudioMode.g7231
--		"EM_AudioMode_g7231">--
--<OSS.FIELDNAME
--		MULTIMEDIA-SYSTEM-CONTROL.AudioMode.g7231.noSilenceSuppressionLowRate
--		"noSilenceSuppressionLowRate">--
--<OSS.DefineName
--		MULTIMEDIA-SYSTEM-CONTROL.AudioMode.g7231.noSilenceSuppressionLowRate
--		"EM_noSilenceSuppressionLowRate">--
--<OSS.FIELDNAME
--		MULTIMEDIA-SYSTEM-CONTROL.AudioMode.g7231.noSilenceSuppressionHighRate
--		"noSilenceSuppressionHighRate">--
--<OSS.DefineName
--		MULTIMEDIA-SYSTEM-CONTROL.AudioMode.g7231.noSilenceSuppressionHighRate
--		"EM_noSilenceSuppressionHighRate">--
--<OSS.FIELDNAME
--		MULTIMEDIA-SYSTEM-CONTROL.AudioMode.g7231.silenceSuppressionLowRate
--		"silenceSuppressionLowRate">--
--<OSS.DefineName
--		MULTIMEDIA-SYSTEM-CONTROL.AudioMode.g7231.silenceSuppressionLowRate
--		"EM_silenceSuppressionLowRate">--
--<OSS.FIELDNAME
--		MULTIMEDIA-SYSTEM-CONTROL.AudioMode.g7231.silenceSuppressionHighRate
--		"silenceSuppressionHighRate">--
--<OSS.DefineName
--		MULTIMEDIA-SYSTEM-CONTROL.AudioMode.g7231.silenceSuppressionHighRate
--		"EM_silenceSuppressionHighRate">--
--<OSS.FIELDNAME
--		MULTIMEDIA-SYSTEM-CONTROL.AudioMode.is11172AudioMode
--		"is11172AudioMode">--
--<OSS.DefineName
--		MULTIMEDIA-SYSTEM-CONTROL.AudioMode.is11172AudioMode
--		"EM_is11172AudioMode">--
--<OSS.FIELDNAME
--		MULTIMEDIA-SYSTEM-CONTROL.AudioMode.is13818AudioMode
--		"is13818AudioMode">--
--<OSS.DefineName
--		MULTIMEDIA-SYSTEM-CONTROL.AudioMode.is13818AudioMode
--		"EM_is13818AudioMode">--
--<OSS.FIELDNAME
--		MULTIMEDIA-SYSTEM-CONTROL.AudioMode.g729wAnnexB
--		"g729wAnnexB">--
--<OSS.DefineName
--		MULTIMEDIA-SYSTEM-CONTROL.AudioMode.g729wAnnexB
--		"EM_AudioMode_g729wAnnexB">--
--<OSS.FIELDNAME
--		MULTIMEDIA-SYSTEM-CONTROL.AudioMode.g729AnnexAwAnnexB
--		"g729AnnexAwAnnexB">--
--<OSS.DefineName
--		MULTIMEDIA-SYSTEM-CONTROL.AudioMode.g729AnnexAwAnnexB
--		"EM_AudioMode_g729AnnexAwAnnexB">--
--<OSS.FIELDNAME
--		MULTIMEDIA-SYSTEM-CONTROL.AudioMode.g7231AnnexCMode
--		"g7231AnnexCMode">--
--<OSS.DefineName
--		MULTIMEDIA-SYSTEM-CONTROL.AudioMode.g7231AnnexCMode
--		"EM_g7231AnnexCMode">--
--<OSS.FIELDNAME
--		MULTIMEDIA-SYSTEM-CONTROL.AudioMode.gsmFullRate
--		"gsmFullRate">--
--<OSS.DefineName
--		MULTIMEDIA-SYSTEM-CONTROL.AudioMode.gsmFullRate
--		"EM_AudioMode_gsmFullRate">--
--<OSS.FIELDNAME
--		MULTIMEDIA-SYSTEM-CONTROL.AudioMode.gsmHalfRate
--		"gsmHalfRate">--
--<OSS.DefineName
--		MULTIMEDIA-SYSTEM-CONTROL.AudioMode.gsmHalfRate
--		"EM_AudioMode_gsmHalfRate">--
--<OSS.FIELDNAME
--		MULTIMEDIA-SYSTEM-CONTROL.AudioMode.gsmEnhancedFullRate
--		"gsmEnhancedFullRate">--
--<OSS.DefineName
--		MULTIMEDIA-SYSTEM-CONTROL.AudioMode.gsmEnhancedFullRate
--		"EM_AudioMode_gsmEnhancedFullRate">--

-- -------------------------------------------------------------- --
--
-- IS11172AudioMode    ::= SEQUENCE
-- {
--     audioLayer  CHOICE
--     {
--         audioLayer1 NULL,
--         audioLayer2 NULL,
--         audioLayer3 NULL
--     },
--  
--     audioSampling   CHOICE
--     {
--         audioSampling32k    NULL,
--         audioSampling44k1   NULL,
--         audioSampling48k    NULL
--     },
--  
--     multichannelType    CHOICE
--     {
--         singleChannel       NULL,
--         twoChannelStereo    NULL,
--         twoChannelDual      NULL
--     },
--  
--     bitRate INTEGER (1..448),
--     ...
-- }
--
-- -------------------------------------------------------------- --
 
--<ASN1.PDU
--		MULTIMEDIA-SYSTEM-CONTROL.IS11172AudioMode>--
--<OSS.TYPENAME
--		MULTIMEDIA-SYSTEM-CONTROL.IS11172AudioMode
--		"EmIS11172AudioMode">--
--<OSS.ExtractType
--		MULTIMEDIA-SYSTEM-CONTROL.IS11172AudioMode.audioLayer>--
--<OSS.TYPENAME
--		MULTIMEDIA-SYSTEM-CONTROL.IS11172AudioMode.audioLayer
--		"EmIS11172AudioModeAudioLayer">--
--<OSS.FIELDNAME
--		MULTIMEDIA-SYSTEM-CONTROL.IS11172AudioMode.audioLayer
--		"audioLayer">--
--<OSS.FIELDNAME
--		MULTIMEDIA-SYSTEM-CONTROL.IS11172AudioMode.audioLayer.audioLayer1
--		"audioLayer1">--
--<OSS.DefineName
--		MULTIMEDIA-SYSTEM-CONTROL.IS11172AudioMode.audioLayer.audioLayer1
--		"EM_IS11172_audioLayer1">--
--<OSS.FIELDNAME
--		MULTIMEDIA-SYSTEM-CONTROL.IS11172AudioMode.audioLayer.audioLayer2
--		"audioLayer2">--
--<OSS.DefineName
--		MULTIMEDIA-SYSTEM-CONTROL.IS11172AudioMode.audioLayer.audioLayer2
--		"EM_IS11172_audioLayer2">--
--<OSS.FIELDNAME
--		MULTIMEDIA-SYSTEM-CONTROL.IS11172AudioMode.audioLayer.audioLayer3
--		"audioLayer3">--
--<OSS.DefineName
--		MULTIMEDIA-SYSTEM-CONTROL.IS11172AudioMode.audioLayer.audioLayer3
--		"EM_IS11172_audioLayer3">--
--<OSS.ExtractType
--		MULTIMEDIA-SYSTEM-CONTROL.IS11172AudioMode.audioSampling>--
--<OSS.TYPENAME
--		MULTIMEDIA-SYSTEM-CONTROL.IS11172AudioMode.audioSampling
--		"EmIS11172AudioModeAudioSampling">--
--<OSS.FIELDNAME
--		MULTIMEDIA-SYSTEM-CONTROL.IS11172AudioMode.audioSampling
--		"audioSampling">--
--<OSS.FIELDNAME
--		MULTIMEDIA-SYSTEM-CONTROL.IS11172AudioMode.audioSampling.audioSampling32k
--		"audioSampling32k">--
--<OSS.DefineName
--		MULTIMEDIA-SYSTEM-CONTROL.IS11172AudioMode.audioSampling.audioSampling32k
--		"EM_IS11172_audioSampling32k">--
--<OSS.FIELDNAME
--		MULTIMEDIA-SYSTEM-CONTROL.IS11172AudioMode.audioSampling.audioSampling44k1
--		"audioSampling44k1">--
--<OSS.DefineName
--		MULTIMEDIA-SYSTEM-CONTROL.IS11172AudioMode.audioSampling.audioSampling44k1
--		"EM_IS11172_audioSampling44k1">--
--<OSS.FIELDNAME
--		MULTIMEDIA-SYSTEM-CONTROL.IS11172AudioMode.audioSampling.audioSampling48k
--		"audioSampling48k">--
--<OSS.DefineName
--		MULTIMEDIA-SYSTEM-CONTROL.IS11172AudioMode.audioSampling.audioSampling48k
--		"EM_IS11172_audioSampling48k">--
--<OSS.ExtractType
--		MULTIMEDIA-SYSTEM-CONTROL.IS11172AudioMode.multichannelType>--
--<OSS.TYPENAME
--		MULTIMEDIA-SYSTEM-CONTROL.IS11172AudioMode.multichannelType
--		"EmIS11172AudioModeMultichannelType">--
--<OSS.FIELDNAME
--		MULTIMEDIA-SYSTEM-CONTROL.IS11172AudioMode.multichannelType
--		"multichannelType">--
--<OSS.FIELDNAME
--		MULTIMEDIA-SYSTEM-CONTROL.IS11172AudioMode.multichannelType.singleChannel
--		"singleChannel">--
--<OSS.DefineName
--		MULTIMEDIA-SYSTEM-CONTROL.IS11172AudioMode.multichannelType.singleChannel
--		"EM_IS11172_singleChannel">--
--<OSS.FIELDNAME
--		MULTIMEDIA-SYSTEM-CONTROL.IS11172AudioMode.multichannelType.twoChannelStereo
--		"twoChannelStereo">--
--<OSS.DefineName
--		MULTIMEDIA-SYSTEM-CONTROL.IS11172AudioMode.multichannelType.twoChannelStereo
--		"EM_IS11172_twoChannelStereo">--
--<OSS.FIELDNAME
--		MULTIMEDIA-SYSTEM-CONTROL.IS11172AudioMode.multichannelType.twoChannelDual
--		"twoChannelDual">--
--<OSS.DefineName
--		MULTIMEDIA-SYSTEM-CONTROL.IS11172AudioMode.multichannelType.twoChannelDual
--		"EM_IS11172_twoChannelDual">--
--<OSS.FIELDNAME
--		MULTIMEDIA-SYSTEM-CONTROL.IS11172AudioMode.bitRate
--		"bitRate">--

-- -------------------------------------------------------------- --
--
-- IS13818AudioMode    ::= SEQUENCE
-- {
--     audioLayer  CHOICE
--     {
--         audioLayer1 NULL,
--         audioLayer2 NULL,
--         audioLayer3 NULL
--     },
--  
--     audioSampling   CHOICE
--     {
--         audioSampling16k    NULL,
--         audioSampling22k05  NULL,
--         audioSampling24k    NULL,
--         audioSampling32k    NULL,
--         audioSampling44k1   NULL,
--         audioSampling48k    NULL
--     },
--  
--     multichannelType    CHOICE
--     {
--         singleChannel       NULL,
--         twoChannelStereo    NULL,
--         twoChannelDual      NULL,
--         threeChannels2-1    NULL,
--         threeChannels3-0    NULL,
--         fourChannels2-0-2-0 NULL,
--         fourChannels2-2     NULL,
--         fourChannels3-1     NULL,
--         fiveChannels3-0-2-0 NULL,
--         fiveChannels3-2     NULL
--     },
--  
--     lowFrequencyEnhancement BOOLEAN,
--  
--     multilingual    BOOLEAN,
--  
--     bitRate INTEGER (1..1130),
--     ...
-- }
--
-- -------------------------------------------------------------- --
 
--<ASN1.PDU
--		MULTIMEDIA-SYSTEM-CONTROL.IS13818AudioMode>--
--<OSS.TYPENAME
--		MULTIMEDIA-SYSTEM-CONTROL.IS13818AudioMode
--		"EmIS13818AudioMode">--
--<OSS.ExtractType
--		MULTIMEDIA-SYSTEM-CONTROL.IS13818AudioMode.audioLayer>--
--<OSS.TYPENAME
--		MULTIMEDIA-SYSTEM-CONTROL.IS13818AudioMode.audioLayer
--		"EmIS13818AudioModeAudioLayer">--
--<OSS.FIELDNAME
--		MULTIMEDIA-SYSTEM-CONTROL.IS13818AudioMode.audioLayer
--		"audioLayer">--
--<OSS.FIELDNAME
--		MULTIMEDIA-SYSTEM-CONTROL.IS13818AudioMode.audioLayer.audioLayer1
--		"audioLayer1">--
--<OSS.DefineName
--		MULTIMEDIA-SYSTEM-CONTROL.IS13818AudioMode.audioLayer.audioLayer1
--		"EM_IS13818_audioLayer1">--
--<OSS.FIELDNAME
--		MULTIMEDIA-SYSTEM-CONTROL.IS13818AudioMode.audioLayer.audioLayer2
--		"audioLayer2">--
--<OSS.DefineName
--		MULTIMEDIA-SYSTEM-CONTROL.IS13818AudioMode.audioLayer.audioLayer2
--		"EM_IS13818_audioLayer2">--
--<OSS.FIELDNAME
--		MULTIMEDIA-SYSTEM-CONTROL.IS13818AudioMode.audioLayer.audioLayer3
--		"audioLayer3">--
--<OSS.DefineName
--		MULTIMEDIA-SYSTEM-CONTROL.IS13818AudioMode.audioLayer.audioLayer3
--		"EM_IS13818_audioLayer3">--
--<OSS.ExtractType
--		MULTIMEDIA-SYSTEM-CONTROL.IS13818AudioMode.audioSampling>--
--<OSS.TYPENAME
--		MULTIMEDIA-SYSTEM-CONTROL.IS13818AudioMode.audioSampling
--		"EmIS13818AudioModeAudioSampling">--
--<OSS.FIELDNAME
--		MULTIMEDIA-SYSTEM-CONTROL.IS13818AudioMode.audioSampling
--		"audioSampling">--
--<OSS.FIELDNAME
--		MULTIMEDIA-SYSTEM-CONTROL.IS13818AudioMode.audioSampling.audioSampling16k
--		"audioSampling16k">--
--<OSS.DefineName
--		MULTIMEDIA-SYSTEM-CONTROL.IS13818AudioMode.audioSampling.audioSampling16k
--		"EM_audioSampling16k">--
--<OSS.FIELDNAME
--		MULTIMEDIA-SYSTEM-CONTROL.IS13818AudioMode.audioSampling.audioSampling22k05
--		"audioSampling22k05">--
--<OSS.DefineName
--		MULTIMEDIA-SYSTEM-CONTROL.IS13818AudioMode.audioSampling.audioSampling22k05
--		"EM_audioSampling22k05">--
--<OSS.FIELDNAME
--		MULTIMEDIA-SYSTEM-CONTROL.IS13818AudioMode.audioSampling.audioSampling24k
--		"audioSampling24k">--
--<OSS.DefineName
--		MULTIMEDIA-SYSTEM-CONTROL.IS13818AudioMode.audioSampling.audioSampling24k
--		"EM_audioSampling24k">--
--<OSS.FIELDNAME
--		MULTIMEDIA-SYSTEM-CONTROL.IS13818AudioMode.audioSampling.audioSampling32k
--		"audioSampling32k">--
--<OSS.DefineName
--		MULTIMEDIA-SYSTEM-CONTROL.IS13818AudioMode.audioSampling.audioSampling32k
--		"EM_IS13818_audioSampling32k">--
--<OSS.FIELDNAME
--		MULTIMEDIA-SYSTEM-CONTROL.IS13818AudioMode.audioSampling.audioSampling44k1
--		"audioSampling44k1">--
--<OSS.DefineName
--		MULTIMEDIA-SYSTEM-CONTROL.IS13818AudioMode.audioSampling.audioSampling44k1
--		"EM_IS13818_audioSampling44k1">--
--<OSS.FIELDNAME
--		MULTIMEDIA-SYSTEM-CONTROL.IS13818AudioMode.audioSampling.audioSampling48k
--		"audioSampling48k">--
--<OSS.DefineName
--		MULTIMEDIA-SYSTEM-CONTROL.IS13818AudioMode.audioSampling.audioSampling48k
--		"EM_IS13818_audioSampling48k">--
--<OSS.ExtractType
--		MULTIMEDIA-SYSTEM-CONTROL.IS13818AudioMode.multichannelType>--
--<OSS.TYPENAME
--		MULTIMEDIA-SYSTEM-CONTROL.IS13818AudioMode.multichannelType
--		"EmIS13818AudioModeMultichannelType">--
--<OSS.FIELDNAME
--		MULTIMEDIA-SYSTEM-CONTROL.IS13818AudioMode.multichannelType
--		"multichannelType">--
--<OSS.FIELDNAME
--		MULTIMEDIA-SYSTEM-CONTROL.IS13818AudioMode.multichannelType.singleChannel
--		"singleChannel">--
--<OSS.DefineName
--		MULTIMEDIA-SYSTEM-CONTROL.IS13818AudioMode.multichannelType.singleChannel
--		"EM_IS13818_singleChannel">--
--<OSS.FIELDNAME
--		MULTIMEDIA-SYSTEM-CONTROL.IS13818AudioMode.multichannelType.twoChannelStereo
--		"twoChannelStereo">--
--<OSS.DefineName
--		MULTIMEDIA-SYSTEM-CONTROL.IS13818AudioMode.multichannelType.twoChannelStereo
--		"EM_IS13818_twoChannelStereo">--
--<OSS.FIELDNAME
--		MULTIMEDIA-SYSTEM-CONTROL.IS13818AudioMode.multichannelType.twoChannelDual
--		"twoChannelDual">--
--<OSS.DefineName
--		MULTIMEDIA-SYSTEM-CONTROL.IS13818AudioMode.multichannelType.twoChannelDual
--		"EM_IS13818_twoChannelDual">--
--<OSS.FIELDNAME
--		MULTIMEDIA-SYSTEM-CONTROL.IS13818AudioMode.multichannelType.threeChannels2-1
--		"threeChannels2_1">--
--<OSS.DefineName
--		MULTIMEDIA-SYSTEM-CONTROL.IS13818AudioMode.multichannelType.threeChannels2-1
--		"EM_threeChannels2_1">--
--<OSS.FIELDNAME
--		MULTIMEDIA-SYSTEM-CONTROL.IS13818AudioMode.multichannelType.threeChannels3-0
--		"threeChannels3_0">--
--<OSS.DefineName
--		MULTIMEDIA-SYSTEM-CONTROL.IS13818AudioMode.multichannelType.threeChannels3-0
--		"EM_threeChannels3_0">--
--<OSS.FIELDNAME
--		MULTIMEDIA-SYSTEM-CONTROL.IS13818AudioMode.multichannelType.fourChannels2-0-2-0
--		"fourChannels2_0_2_0">--
--<OSS.DefineName
--		MULTIMEDIA-SYSTEM-CONTROL.IS13818AudioMode.multichannelType.fourChannels2-0-2-0
--		"EM_fourChannels2_0_2_0">--
--<OSS.FIELDNAME
--		MULTIMEDIA-SYSTEM-CONTROL.IS13818AudioMode.multichannelType.fourChannels2-2
--		"fourChannels2_2">--
--<OSS.DefineName
--		MULTIMEDIA-SYSTEM-CONTROL.IS13818AudioMode.multichannelType.fourChannels2-2
--		"EM_fourChannels2_2">--
--<OSS.FIELDNAME
--		MULTIMEDIA-SYSTEM-CONTROL.IS13818AudioMode.multichannelType.fourChannels3-1
--		"fourChannels3_1">--
--<OSS.DefineName
--		MULTIMEDIA-SYSTEM-CONTROL.IS13818AudioMode.multichannelType.fourChannels3-1
--		"EM_fourChannels3_1">--
--<OSS.FIELDNAME
--		MULTIMEDIA-SYSTEM-CONTROL.IS13818AudioMode.multichannelType.fiveChannels3-0-2-0
--		"fiveChannels3_0_2_0">--
--<OSS.DefineName
--		MULTIMEDIA-SYSTEM-CONTROL.IS13818AudioMode.multichannelType.fiveChannels3-0-2-0
--		"EM_fiveChannels3_0_2_0">--
--<OSS.FIELDNAME
--		MULTIMEDIA-SYSTEM-CONTROL.IS13818AudioMode.multichannelType.fiveChannels3-2
--		"fiveChannels3_2">--
--<OSS.DefineName
--		MULTIMEDIA-SYSTEM-CONTROL.IS13818AudioMode.multichannelType.fiveChannels3-2
--		"EM_fiveChannels3_2">--
--<OSS.FIELDNAME
--		MULTIMEDIA-SYSTEM-CONTROL.IS13818AudioMode.lowFrequencyEnhancement
--		"lowFrequencyEnhancement">--
--<OSS.FIELDNAME
--		MULTIMEDIA-SYSTEM-CONTROL.IS13818AudioMode.multilingual
--		"multilingual">--
--<OSS.FIELDNAME
--		MULTIMEDIA-SYSTEM-CONTROL.IS13818AudioMode.bitRate
--		"bitRate">--

-- -------------------------------------------------------------- --
--
-- G7231AnnexCMode ::= SEQUENCE
-- {
--     maxAl-sduAudioFrames    INTEGER (1..256),
--     silenceSuppression      BOOLEAN,
--     g723AnnexCAudioMode	   G723AnnexCAudioMode,
--     ...
-- }
--
-- -------------------------------------------------------------- --

--<ASN1.PDU
--		MULTIMEDIA-SYSTEM-CONTROL.G7231AnnexCMode>--
--<OSS.TYPENAME
--		MULTIMEDIA-SYSTEM-CONTROL.G7231AnnexCMode
--		"EmG7231AnnexCMode">--
--<OSS.FIELDNAME
--		MULTIMEDIA-SYSTEM-CONTROL.G7231AnnexCMode.maxAl-sduAudioFrames
--		"sduAudioFrames">--
--<OSS.FIELDNAME
--		MULTIMEDIA-SYSTEM-CONTROL.G7231AnnexCMode.silenceSuppression
--		"silenceSuppression">--
--<OSS.FIELDNAME
--		MULTIMEDIA-SYSTEM-CONTROL.G7231AnnexCMode.g723AnnexCAudioMode
--		"g723AnnexCAudioMode">--

-- ==============================================================
-- Request mode definitions: Data modes
-- ==============================================================
 
-- -------------------------------------------------------------- --
--
-- DataMode        ::= SEQUENCE
-- {
--     application CHOICE
--     {
--         nonStandard NonStandardParameter,
--         t120        DataProtocolCapability,
--         dsm-cc      DataProtocolCapability,
--         userData    DataProtocolCapability,
--         t84         DataProtocolCapability,
--         t434        DataProtocolCapability,
--         h224        DataProtocolCapability,
--         nlpid   SEQUENCE
--         {
--             nlpidProtocol   DataProtocolCapability,
--             nlpidData       OCTET STRING
--         },
--         dsvdControl NULL,
--         h222DataPartitioning    DataProtocolCapability,
--         ...,
--         t30fax      DataProtocolCapability,
--         t140        DataProtocolCapability
--		t38fax				SEQUENCE
--		{
--			t38faxProtocol		DataProtocolCapability,
--			t38faxRateMgmnt		T38faxRateMgmnt,
--			t38faxProfile		T38faxProfile,
--			...
--		}
--     },
--     bitRate INTEGER (0..4294967295),
--     ...
-- }
--
-- -------------------------------------------------------------- --

--<ASN1.PDU
--		MULTIMEDIA-SYSTEM-CONTROL.DataMode>--
--<OSS.TYPENAME
--		MULTIMEDIA-SYSTEM-CONTROL.DataMode
--		"EmDataMode">--
--<OSS.ExtractType
--		MULTIMEDIA-SYSTEM-CONTROL.DataMode.application>--
--<OSS.TYPENAME
--		MULTIMEDIA-SYSTEM-CONTROL.DataMode.application
--		"EmDataModeApplication">--
--<OSS.FIELDNAME
--		MULTIMEDIA-SYSTEM-CONTROL.DataMode.application
--		"application">--
--<OSS.FIELDNAME
--		MULTIMEDIA-SYSTEM-CONTROL.DataMode.application.nonStandard
--		"nonStandard">--
--<OSS.DefineName
--		MULTIMEDIA-SYSTEM-CONTROL.DataMode.application.nonStandard
--		"EM_DataModeApplication_nonStandard">--
--<OSS.FIELDNAME
--		MULTIMEDIA-SYSTEM-CONTROL.DataMode.application.t120
--		"t120">--
--<OSS.DefineName
--		MULTIMEDIA-SYSTEM-CONTROL.DataMode.application.t120
--		"EM_DataModeApplication_t120">--
--<OSS.FIELDNAME
--		MULTIMEDIA-SYSTEM-CONTROL.DataMode.application.dsm-cc
--		"dsm_cc">--
--<OSS.DefineName
--		MULTIMEDIA-SYSTEM-CONTROL.DataMode.application.dsm-cc
--		"EM_DataModeApplication_dsm_cc">--
--<OSS.FIELDNAME
--		MULTIMEDIA-SYSTEM-CONTROL.DataMode.application.userData
--		"userData">--
--<OSS.DefineName
--		MULTIMEDIA-SYSTEM-CONTROL.DataMode.application.userData
--		"EM_DataModeApplication_userData">--
--<OSS.FIELDNAME
--		MULTIMEDIA-SYSTEM-CONTROL.DataMode.application.t84
--		"t84">--
--<OSS.DefineName
--		MULTIMEDIA-SYSTEM-CONTROL.DataMode.application.t84
--		"EM_DataModeApplication_t84">--
--<OSS.FIELDNAME
--		MULTIMEDIA-SYSTEM-CONTROL.DataMode.application.t434
--		"t434">--
--<OSS.DefineName
--		MULTIMEDIA-SYSTEM-CONTROL.DataMode.application.t434
--		"EM_DataModeApplication_t434">--
--<OSS.FIELDNAME
--		MULTIMEDIA-SYSTEM-CONTROL.DataMode.application.h224
--		"h224">--
--<OSS.DefineName
--		MULTIMEDIA-SYSTEM-CONTROL.DataMode.application.h224
--		"EM_DataModeApplication_h224">--
--<OSS.InlineType
--		MULTIMEDIA-SYSTEM-CONTROL.DataMode.application.nlpid>--
--<OSS.TYPENAME
--		MULTIMEDIA-SYSTEM-CONTROL.DataMode.application.nlpid
--		"EmDataModeNlpid">--
--<OSS.FIELDNAME
--		MULTIMEDIA-SYSTEM-CONTROL.DataMode.application.nlpid
--		"nlpid">--
--<OSS.DefineName
--		MULTIMEDIA-SYSTEM-CONTROL.DataMode.application.nlpid
--		"EM_DataModeApplication_nlpid">--
--<OSS.FIELDNAME
--		MULTIMEDIA-SYSTEM-CONTROL.DataMode.application.nlpid.nlpidProtocol
--		"nlpidProtocol">--
--<OSS.FIELDNAME
--		MULTIMEDIA-SYSTEM-CONTROL.DataMode.application.nlpid.nlpidData
--		"nlpidData">--
--<OSS.FIELDNAME
--		MULTIMEDIA-SYSTEM-CONTROL.DataMode.application.dsvdControl
--		"dsvdControl">--
--<OSS.DefineName
--		MULTIMEDIA-SYSTEM-CONTROL.DataMode.application.dsvdControl
--		"EM_DataModeApplication_dsvdControl">--
--<OSS.FIELDNAME
--		MULTIMEDIA-SYSTEM-CONTROL.DataMode.application.h222DataPartitioning
--		"h222DataPartitioning">--
--<OSS.DefineName
--		MULTIMEDIA-SYSTEM-CONTROL.DataMode.application.h222DataPartitioning
--		"EM_DataModeApplication_h222DataPartitioning">--
--<OSS.FIELDNAME
--		MULTIMEDIA-SYSTEM-CONTROL.DataMode.application.t30fax
--		"t30fax">--
--<OSS.DefineName
--		MULTIMEDIA-SYSTEM-CONTROL.DataMode.application.t30fax
--		"EM_DataModeApplication_t30fax">--
--<OSS.FIELDNAME
--		MULTIMEDIA-SYSTEM-CONTROL.DataMode.application.t140
--		"t140">--
--<OSS.DefineName
--		MULTIMEDIA-SYSTEM-CONTROL.DataMode.application.t140
--		"EM_DataModeApplication_t140">--
--<OSS.InlineType
--		MULTIMEDIA-SYSTEM-CONTROL.DataMode.application.t38fax>--
--<OSS.TYPENAME
--		MULTIMEDIA-SYSTEM-CONTROL.DataMode.application.t38fax
--		"EmT38fax">--
--<OSS.FIELDNAME
--		MULTIMEDIA-SYSTEM-CONTROL.DataMode.application.t38fax
--		"t38fax">--
--<OSS.DefineName
--		MULTIMEDIA-SYSTEM-CONTROL.DataMode.application.t38fax
--		"EM_Application_t38fax">--
--<OSS.FIELDNAME
--		MULTIMEDIA-SYSTEM-CONTROL.DataMode.bitRate
--		"bitRate">--

-- ==============================================================
-- Request mode definitions: Encryption modes
-- ==============================================================
 
-- -------------------------------------------------------------- --
--
-- EncryptionMode  ::= CHOICE
-- {
--     nonStandard NonStandardParameter,
--     h233Encryption  NULL,
--     ...
-- }
--
-- -------------------------------------------------------------- --
 
--<ASN1.PDU
--		MULTIMEDIA-SYSTEM-CONTROL.EncryptionMode>--
--<OSS.TYPENAME
--		MULTIMEDIA-SYSTEM-CONTROL.EncryptionMode
--		"EmEncryptionMode">--
--<OSS.FIELDNAME
--		MULTIMEDIA-SYSTEM-CONTROL.EncryptionMode.nonStandard
--		"nonStandard">--
--<OSS.DefineName
--		MULTIMEDIA-SYSTEM-CONTROL.EncryptionMode.nonStandard
--		"EM_EncryptionMode_nonStandard">--
--<OSS.FIELDNAME
--		MULTIMEDIA-SYSTEM-CONTROL.EncryptionMode.h233Encryption
--		"h233Encryption">--
--<OSS.DefineName
--		MULTIMEDIA-SYSTEM-CONTROL.EncryptionMode.h233Encryption
--		"EM_h233Encryption">--

-- ==============================================================
-- Round Trip Delay definitions
-- ==============================================================
 
-- -------------------------------------------------------------- --
--
-- RoundTripDelayRequest   ::= SEQUENCE
-- {
--     sequenceNumber  SequenceNumber,
--     ...
-- }
--
-- -------------------------------------------------------------- --
 
--<ASN1.PDU
--		MULTIMEDIA-SYSTEM-CONTROL.RoundTripDelayRequest>--
--<OSS.TYPENAME
--		MULTIMEDIA-SYSTEM-CONTROL.RoundTripDelayRequest
--		"EmRoundTripDelayRequest">--
--<OSS.FIELDNAME
--		MULTIMEDIA-SYSTEM-CONTROL.RoundTripDelayRequest.sequenceNumber
--		"sequenceNumber">--

-- -------------------------------------------------------------- --
--
-- RoundTripDelayResponse  ::= SEQUENCE
-- {
--     sequenceNumber  SequenceNumber,
--     ...
-- }
--
-- -------------------------------------------------------------- --
 
--<ASN1.PDU
--		MULTIMEDIA-SYSTEM-CONTROL.RoundTripDelayResponse>--
--<OSS.TYPENAME
--		MULTIMEDIA-SYSTEM-CONTROL.RoundTripDelayResponse
--		"EmRoundTripDelayResponse">--
--<OSS.FIELDNAME
--		MULTIMEDIA-SYSTEM-CONTROL.RoundTripDelayResponse.sequenceNumber
--		"sequenceNumber">--

-- ==============================================================
-- Maintenance Loop definitions
-- ==============================================================
 
-- -------------------------------------------------------------- --
--  
-- MaintenanceLoopRequest  ::= SEQUENCE
-- {
--     type        CHOICE
--     {
--         systemLoop          NULL,
--         mediaLoop           LogicalChannelNumber,
--         logicalChannelLoop  LogicalChannelNumber,
--         ...
--     },
--     ...
-- }
--  
-- -------------------------------------------------------------- --

--<ASN1.PDU
--		MULTIMEDIA-SYSTEM-CONTROL.MaintenanceLoopRequest>--
--<OSS.TYPENAME
--		MULTIMEDIA-SYSTEM-CONTROL.MaintenanceLoopRequest
--		"EmMaintenanceLoopRequest">--
--<OSS.ExtractType
--		MULTIMEDIA-SYSTEM-CONTROL.MaintenanceLoopRequest.type>--
--<OSS.TYPENAME
--		MULTIMEDIA-SYSTEM-CONTROL.MaintenanceLoopRequest.type
--		"EmMaintenanceLoopRequestType">--
--<OSS.FIELDNAME
--		MULTIMEDIA-SYSTEM-CONTROL.MaintenanceLoopRequest.type
--		"type">--
--<OSS.FIELDNAME
--		MULTIMEDIA-SYSTEM-CONTROL.MaintenanceLoopRequest.type.systemLoop
--		"systemLoop">--
--<OSS.DefineName
--		MULTIMEDIA-SYSTEM-CONTROL.MaintenanceLoopRequest.type.systemLoop
--		"EM_MaintenanceLoopRequest_systemLoop">--
--<OSS.FIELDNAME
--		MULTIMEDIA-SYSTEM-CONTROL.MaintenanceLoopRequest.type.mediaLoop
--		"mediaLoop">--
--<OSS.DefineName
--		MULTIMEDIA-SYSTEM-CONTROL.MaintenanceLoopRequest.type.mediaLoop
--		"EM_MaintenanceLoopRequest_mediaLoop">--
--<OSS.FIELDNAME
--		MULTIMEDIA-SYSTEM-CONTROL.MaintenanceLoopRequest.type.logicalChannelLoop
--		"logicalChannelLoop">--
--<OSS.DefineName
--		MULTIMEDIA-SYSTEM-CONTROL.MaintenanceLoopRequest.type.logicalChannelLoop
--		"EM_MaintenanceLoopRequest_logicalChannelLoop">--

-- -------------------------------------------------------------- --
--  
-- MaintenanceLoopAck  ::= SEQUENCE
-- {
--     type        CHOICE
--     {
--         systemLoop          NULL,
--         mediaLoop           LogicalChannelNumber,
--         logicalChannelLoop  LogicalChannelNumber,
--         ...
--     },
--     ...
-- }
--  
-- -------------------------------------------------------------- --

--<ASN1.PDU
--		MULTIMEDIA-SYSTEM-CONTROL.MaintenanceLoopAck>--
--<OSS.TYPENAME
--		MULTIMEDIA-SYSTEM-CONTROL.MaintenanceLoopAck
--		"EmMaintenanceLoopAck">--
--<OSS.ExtractType
--		MULTIMEDIA-SYSTEM-CONTROL.MaintenanceLoopAck.type>--
--<OSS.TYPENAME
--		MULTIMEDIA-SYSTEM-CONTROL.MaintenanceLoopAck.type
--		"EmMaintenanceLoopAckType">--
--<OSS.FIELDNAME
--		MULTIMEDIA-SYSTEM-CONTROL.MaintenanceLoopAck.type
--		"type">--
--<OSS.FIELDNAME
--		MULTIMEDIA-SYSTEM-CONTROL.MaintenanceLoopAck.type.systemLoop
--		"systemLoop">--
--<OSS.DefineName
--		MULTIMEDIA-SYSTEM-CONTROL.MaintenanceLoopAck.type.systemLoop
--		"EM_MaintenanceLoopAck_systemLoop">--
--<OSS.FIELDNAME
--		MULTIMEDIA-SYSTEM-CONTROL.MaintenanceLoopAck.type.mediaLoop
--		"mediaLoop">--
--<OSS.DefineName
--		MULTIMEDIA-SYSTEM-CONTROL.MaintenanceLoopAck.type.mediaLoop
--		"EM_MaintenanceLoopAck_mediaLoop">--
--<OSS.FIELDNAME
--		MULTIMEDIA-SYSTEM-CONTROL.MaintenanceLoopAck.type.logicalChannelLoop
--		"logicalChannelLoop">--
--<OSS.DefineName
--		MULTIMEDIA-SYSTEM-CONTROL.MaintenanceLoopAck.type.logicalChannelLoop
--		"EM_MaintenanceLoopAck_logicalChannelLoop">--

-- -------------------------------------------------------------- --
--  
-- MaintenanceLoopReject   ::= SEQUENCE
-- {
--     type        CHOICE
--     {
--         systemLoop          NULL,
--         mediaLoop           LogicalChannelNumber,
--         logicalChannelLoop  LogicalChannelNumber,
--         ...
--     },
--     cause       CHOICE
--     {
--         canNotPerformLoop   NULL,
--         ...
--     },
--     ...
-- }
--  
-- -------------------------------------------------------------- --

--<ASN1.PDU
--		MULTIMEDIA-SYSTEM-CONTROL.MaintenanceLoopReject>--
--<OSS.TYPENAME
--		MULTIMEDIA-SYSTEM-CONTROL.MaintenanceLoopReject
--		"EmMaintenanceLoopReject">--
--<OSS.ExtractType
--		MULTIMEDIA-SYSTEM-CONTROL.MaintenanceLoopReject.type>--
--<OSS.TYPENAME
--		MULTIMEDIA-SYSTEM-CONTROL.MaintenanceLoopReject.type
--		"EmMaintenanceLoopRejectType">--
--<OSS.FIELDNAME
--		MULTIMEDIA-SYSTEM-CONTROL.MaintenanceLoopReject.type
--		"type">--
--<OSS.FIELDNAME
--		MULTIMEDIA-SYSTEM-CONTROL.MaintenanceLoopReject.type.systemLoop
--		"systemLoop">--
--<OSS.DefineName
--		MULTIMEDIA-SYSTEM-CONTROL.MaintenanceLoopReject.type.systemLoop
--		"EM_MaintenanceLoopReject_systemLoop">--
--<OSS.FIELDNAME
--		MULTIMEDIA-SYSTEM-CONTROL.MaintenanceLoopReject.type.mediaLoop
--		"mediaLoop">--
--<OSS.DefineName
--		MULTIMEDIA-SYSTEM-CONTROL.MaintenanceLoopReject.type.mediaLoop
--		"EM_MaintenanceLoopReject_mediaLoop">--
--<OSS.FIELDNAME
--		MULTIMEDIA-SYSTEM-CONTROL.MaintenanceLoopReject.type.logicalChannelLoop
--		"logicalChannelLoop">--
--<OSS.DefineName
--		MULTIMEDIA-SYSTEM-CONTROL.MaintenanceLoopReject.type.logicalChannelLoop
--		"EM_MaintenanceLoopReject_logicalChannelLoop">--
--<OSS.ExtractType
--		MULTIMEDIA-SYSTEM-CONTROL.MaintenanceLoopReject.cause>--
--<OSS.TYPENAME
--		MULTIMEDIA-SYSTEM-CONTROL.MaintenanceLoopReject.cause
--		"EmMaintenanceLoopRejectCause">--
--<OSS.FIELDNAME
--		MULTIMEDIA-SYSTEM-CONTROL.MaintenanceLoopReject.cause
--		"cause">--
--<OSS.FIELDNAME
--		MULTIMEDIA-SYSTEM-CONTROL.MaintenanceLoopReject.cause.canNotPerformLoop
--		"canNotPerformLoop">--
--<OSS.DefineName
--		MULTIMEDIA-SYSTEM-CONTROL.MaintenanceLoopReject.cause.canNotPerformLoop
--		"EM_canNotPerformLoop">--

-- -------------------------------------------------------------- --
--  
-- MaintenanceLoopOffCommand   ::= SEQUENCE
-- {
--     ...
-- }
--
-- -------------------------------------------------------------- --

--<ASN1.PDU
--		MULTIMEDIA-SYSTEM-CONTROL.MaintenanceLoopOffCommand>--
--<OSS.TYPENAME
--		MULTIMEDIA-SYSTEM-CONTROL.MaintenanceLoopOffCommand
--		"EmMaintenanceLoopOffCommand">--

-- ==============================================================
-- Communication Mode definitions
-- ==============================================================

-- -------------------------------------------------------------- --
--  
-- CommunicationModeCommand    ::= SEQUENCE
-- {
--     communicationModeTable  SetOf256CommunicationModeTableEntry,
--     ...
-- }
--
-- -------------------------------------------------------------- --

--<ASN1.PDU
--		MULTIMEDIA-SYSTEM-CONTROL.CommunicationModeCommand>--
--<OSS.TYPENAME
--		MULTIMEDIA-SYSTEM-CONTROL.CommunicationModeCommand
--		"EmCommunicationModeCommand">--
--<OSS.FIELDNAME
--		MULTIMEDIA-SYSTEM-CONTROL.CommunicationModeCommand.communicationModeTable
--		"communicationModeTable">--

-- -------------------------------------------------------------- --
--  
-- CommunicationModeRequest    ::= SEQUENCE
-- {
--     ...
-- }
--
-- -------------------------------------------------------------- --

--<ASN1.PDU
--		MULTIMEDIA-SYSTEM-CONTROL.CommunicationModeRequest>--
--<OSS.TYPENAME
--		MULTIMEDIA-SYSTEM-CONTROL.CommunicationModeRequest
--		"EmCommunicationModeRequest">--

-- -------------------------------------------------------------- --
--  
-- CommunicationModeResponse   ::= CHOICE
-- {
--     communicationModeTable  SetOf256CommunicationModeTableEntry,
--     ...
-- }
--
-- -------------------------------------------------------------- --

--<ASN1.PDU
--		MULTIMEDIA-SYSTEM-CONTROL.CommunicationModeResponse>--
--<OSS.TYPENAME
--		MULTIMEDIA-SYSTEM-CONTROL.CommunicationModeResponse
--		"EmCommunicationModeResponse">--
--<OSS.FIELDNAME
--		MULTIMEDIA-SYSTEM-CONTROL.CommunicationModeResponse.communicationModeTable
--		"communicationModeTable">--
--<OSS.DefineName
--		MULTIMEDIA-SYSTEM-CONTROL.CommunicationModeResponse.communicationModeTable
--		"EM_communicationModeTable">--

-- -------------------------------------------------------------- --
--  
-- CommunicationModeTableEntry ::= SEQUENCE
-- {
--     nonStandard             SEQUENCE OF NonStandardParameter OPTIONAL,
--     sessionID               INTEGER(1..255),
--     associatedSessionID     INTEGER(1..255) OPTIONAL,
--  
--     terminalLabel   TerminalLabel   OPTIONAL,
--     sessionDescription  BMPString (SIZE(1..128)),
--     dataType    CHOICE
--     {
--         videoData   VideoCapability,
--         audioData   AudioCapability,
--         data    DataApplicationCapability,
--         ...
--     },
--     mediaChannel    TransportAddress  OPTIONAL,
--     mediaGuaranteedDelivery BOOLEAN  OPTIONAL,
--     mediaControlChannel TransportAddress  OPTIONAL,
--     mediaControlGuaranteedDelivery  BOOLEAN  OPTIONAL,
--     ...,
--     redundancyEncoding      RedundancyEncoding OPTIONAL,
--     sessionDependency       INTEGER (1..255) OPTIONAL,
--     destination             TerminalLabel OPTIONAL
-- }
--
-- -------------------------------------------------------------- --

--<ASN1.PDU
--		MULTIMEDIA-SYSTEM-CONTROL.CommunicationModeTableEntry>--
--<OSS.TYPENAME
--		MULTIMEDIA-SYSTEM-CONTROL.CommunicationModeTableEntry
--		"EmCommunicationModeTableEntry">--
--<OSS.FIELDNAME
--		MULTIMEDIA-SYSTEM-CONTROL.CommunicationModeTableEntry.nonStandard
--		"nonStandard">--
--<OSS.DefineName
--		MULTIMEDIA-SYSTEM-CONTROL.CommunicationModeTableEntry.nonStandard
--		"EM_CommModeTableEntry_nonStandard">--
--<OSS.FIELDNAME
--		MULTIMEDIA-SYSTEM-CONTROL.CommunicationModeTableEntry.sessionID
--		"sessionID">--
--<OSS.FIELDNAME
--		MULTIMEDIA-SYSTEM-CONTROL.CommunicationModeTableEntry.associatedSessionID
--		"associatedSessionID">--
--<OSS.DefineName
--		MULTIMEDIA-SYSTEM-CONTROL.CommunicationModeTableEntry.associatedSessionID
--		"EM_CommModeTableEntry_associatedSessionID">--
--<OSS.FIELDNAME
--		MULTIMEDIA-SYSTEM-CONTROL.CommunicationModeTableEntry.terminalLabel
--		"terminalLabel">--
--<OSS.DefineName
--		MULTIMEDIA-SYSTEM-CONTROL.CommunicationModeTableEntry.terminalLabel
--		"EM_CommModeTableEntry_terminalLabel">--
--<OSS.InlineType
--		MULTIMEDIA-SYSTEM-CONTROL.CommunicationModeTableEntry.sessionDescription>--
--<OSS.TYPENAME
--		MULTIMEDIA-SYSTEM-CONTROL.CommunicationModeTableEntry.sessionDescription
--		"EmSessionDescription">--
--<OSS.FIELDNAME
--		MULTIMEDIA-SYSTEM-CONTROL.CommunicationModeTableEntry.sessionDescription
--		"sessionDescription">--
--<OSS.ExtractType
--		MULTIMEDIA-SYSTEM-CONTROL.CommunicationModeTableEntry.dataType>--
--<OSS.TYPENAME
--		MULTIMEDIA-SYSTEM-CONTROL.CommunicationModeTableEntry.dataType
--		"EmCommunicationModeTableEntryDataType">--
--<OSS.FIELDNAME
--		MULTIMEDIA-SYSTEM-CONTROL.CommunicationModeTableEntry.dataType
--		"dataType">--
--<OSS.FIELDNAME
--		MULTIMEDIA-SYSTEM-CONTROL.CommunicationModeTableEntry.dataType.videoData
--		"videoData">--
--<OSS.DefineName
--		MULTIMEDIA-SYSTEM-CONTROL.CommunicationModeTableEntry.dataType.videoData
--		"EM_CommunicationModeTableEntryDataType_videoData">--
--<OSS.FIELDNAME
--		MULTIMEDIA-SYSTEM-CONTROL.CommunicationModeTableEntry.dataType.audioData
--		"audioData">--
--<OSS.DefineName
--		MULTIMEDIA-SYSTEM-CONTROL.CommunicationModeTableEntry.dataType.audioData
--		"EM_CommunicationModeTableEntryDataType_audioData">--
--<OSS.FIELDNAME
--		MULTIMEDIA-SYSTEM-CONTROL.CommunicationModeTableEntry.dataType.data
--		"data">--
--<OSS.DefineName
--		MULTIMEDIA-SYSTEM-CONTROL.CommunicationModeTableEntry.dataType.data
--		"EM_CommunicationModeTableEntryDataType_data">--
--<OSS.FIELDNAME
--		MULTIMEDIA-SYSTEM-CONTROL.CommunicationModeTableEntry.mediaChannel
--		"mediaChannel">--
--<OSS.DefineName
--		MULTIMEDIA-SYSTEM-CONTROL.CommunicationModeTableEntry.mediaChannel
--		"EM_CommModeTableEntry_mediaChannel">--
--<OSS.FIELDNAME
--		MULTIMEDIA-SYSTEM-CONTROL.CommunicationModeTableEntry.mediaGuaranteedDelivery
--		"mediaGuaranteedDelivery">--
--<OSS.DefineName
--		MULTIMEDIA-SYSTEM-CONTROL.CommunicationModeTableEntry.mediaGuaranteedDelivery
--		"EM_CommModeTableEntry_mediaGuaranteedDelivery">--
--<OSS.FIELDNAME
--		MULTIMEDIA-SYSTEM-CONTROL.CommunicationModeTableEntry.mediaControlChannel
--		"mediaControlChannel">--
--<OSS.DefineName
--		MULTIMEDIA-SYSTEM-CONTROL.CommunicationModeTableEntry.mediaControlChannel
--		"EM_CommModeTableEntry_mediaControlChannel">--
--<OSS.FIELDNAME
--		MULTIMEDIA-SYSTEM-CONTROL.CommunicationModeTableEntry.mediaControlGuaranteedDelivery
--		"mediaControlGuaranteedDelivery">--
--<OSS.DefineName
--		MULTIMEDIA-SYSTEM-CONTROL.CommunicationModeTableEntry.mediaControlGuaranteedDelivery
--		"EM_CommModeTableEntry_mediaControlGuaranteedDelivery">--
--<OSS.FIELDNAME
--		MULTIMEDIA-SYSTEM-CONTROL.CommunicationModeTableEntry.redundancyEncoding
--		"redundancyEncoding">--
--<OSS.DefineName
--		MULTIMEDIA-SYSTEM-CONTROL.CommunicationModeTableEntry.redundancyEncoding
--		"EM_CommModeTableEntry_redundancyEncoding">--
--<OSS.FIELDNAME
--		MULTIMEDIA-SYSTEM-CONTROL.CommunicationModeTableEntry.sessionDependency
--		"sessionDependency">--
--<OSS.DefineName
--		MULTIMEDIA-SYSTEM-CONTROL.CommunicationModeTableEntry.sessionDependency
--		"EM_sessionDependency">--
--<OSS.FIELDNAME
--		MULTIMEDIA-SYSTEM-CONTROL.CommunicationModeTableEntry.destination
--		"destination">--
--<OSS.DefineName
--		MULTIMEDIA-SYSTEM-CONTROL.CommunicationModeTableEntry.destination
--		"EM_CommModeTableEntry_destination">--

-- ==============================================================
-- Conference Request definitions
-- ==============================================================
 
-- -------------------------------------------------------------- --
--
-- ConferenceRequest   ::= CHOICE
-- {
--    
--     terminalListRequest NULL,
--  
--     makeMeChair NULL,
--     cancelMakeMeChair   NULL,
--  
--     dropTerminal    TerminalLabel,
--  
--     requestTerminalID   TerminalLabel,
--  
--     enterH243Password   NULL,
--     enterH243TerminalID NULL,
--     enterH243ConferenceID   NULL,
--     ...,
--     enterExtensionAddress       NULL,
--     requestChairTokenOwner      NULL,
--     requestTerminalCertificate  SEQUENCE
--     {
--         terminalLabel           TerminalLabel OPTIONAL,
--         certSelectionCriteria   CertSelectionCriteria OPTIONAL,
--         sRandom                 INTEGER (1..4294967295) OPTIONAL,
--         ...
--     },
--     broadcastMyLogicalChannel   LogicalChannelNumber,
--     makeTerminalBroadcaster     TerminalLabel,
--     sendThisSource              TerminalLabel,
--     requestAllTerminalIDs       NULL,
--     remoteMCRequest             RemoteMCRequest
-- }
--
-- -------------------------------------------------------------- --

--<ASN1.PDU
--		MULTIMEDIA-SYSTEM-CONTROL.ConferenceRequest>--
--<OSS.TYPENAME
--		MULTIMEDIA-SYSTEM-CONTROL.ConferenceRequest
--		"EmConferenceRequest">--
--<OSS.FIELDNAME
--		MULTIMEDIA-SYSTEM-CONTROL.ConferenceRequest.terminalListRequest
--		"terminalListRequest">--
--<OSS.DefineName
--		MULTIMEDIA-SYSTEM-CONTROL.ConferenceRequest.terminalListRequest
--		"EM_terminalListRequest">--
--<OSS.FIELDNAME
--		MULTIMEDIA-SYSTEM-CONTROL.ConferenceRequest.makeMeChair
--		"makeMeChair">--
--<OSS.DefineName
--		MULTIMEDIA-SYSTEM-CONTROL.ConferenceRequest.makeMeChair
--		"EM_makeMeChair">--
--<OSS.FIELDNAME
--		MULTIMEDIA-SYSTEM-CONTROL.ConferenceRequest.cancelMakeMeChair
--		"cancelMakeMeChair">--
--<OSS.DefineName
--		MULTIMEDIA-SYSTEM-CONTROL.ConferenceRequest.cancelMakeMeChair
--		"EM_cancelMakeMeChair">--
--<OSS.FIELDNAME
--		MULTIMEDIA-SYSTEM-CONTROL.ConferenceRequest.dropTerminal
--		"dropTerminal">--
--<OSS.DefineName
--		MULTIMEDIA-SYSTEM-CONTROL.ConferenceRequest.dropTerminal
--		"EM_dropTerminal">--
--<OSS.FIELDNAME
--		MULTIMEDIA-SYSTEM-CONTROL.ConferenceRequest.requestTerminalID
--		"requestTerminalID">--
--<OSS.DefineName
--		MULTIMEDIA-SYSTEM-CONTROL.ConferenceRequest.requestTerminalID
--		"EM_requestTerminalID">--
--<OSS.FIELDNAME
--		MULTIMEDIA-SYSTEM-CONTROL.ConferenceRequest.enterH243Password
--		"enterH243Password">--
--<OSS.DefineName
--		MULTIMEDIA-SYSTEM-CONTROL.ConferenceRequest.enterH243Password
--		"EM_enterH243Password">--
--<OSS.FIELDNAME
--		MULTIMEDIA-SYSTEM-CONTROL.ConferenceRequest.enterH243TerminalID
--		"enterH243TerminalID">--
--<OSS.DefineName
--		MULTIMEDIA-SYSTEM-CONTROL.ConferenceRequest.enterH243TerminalID
--		"EM_enterH243TerminalID">--
--<OSS.FIELDNAME
--		MULTIMEDIA-SYSTEM-CONTROL.ConferenceRequest.enterH243ConferenceID
--		"enterH243ConferenceID">--
--<OSS.DefineName
--		MULTIMEDIA-SYSTEM-CONTROL.ConferenceRequest.enterH243ConferenceID
--		"EM_enterH243ConferenceID">--
--<OSS.FIELDNAME
--		MULTIMEDIA-SYSTEM-CONTROL.ConferenceRequest.enterExtensionAddress
--		"enterExtensionAddress">--
--<OSS.DefineName
--		MULTIMEDIA-SYSTEM-CONTROL.ConferenceRequest.enterExtensionAddress
--		"EM_enterExtensionAddress">--
--<OSS.FIELDNAME
--		MULTIMEDIA-SYSTEM-CONTROL.ConferenceRequest.requestChairTokenOwner
--		"requestChairTokenOwner">--
--<OSS.DefineName
--		MULTIMEDIA-SYSTEM-CONTROL.ConferenceRequest.requestChairTokenOwner
--		"EM_requestChairTokenOwner">--
--<OSS.ExtractType
--		MULTIMEDIA-SYSTEM-CONTROL.ConferenceRequest.requestTerminalCertificate>--
--<OSS.TYPENAME
--		MULTIMEDIA-SYSTEM-CONTROL.ConferenceRequest.requestTerminalCertificate
--		"EmRequestTerminalCertificate">--
--<OSS.FIELDNAME
--		MULTIMEDIA-SYSTEM-CONTROL.ConferenceRequest.requestTerminalCertificate
--		"requestTerminalCertificate">--
--<OSS.DefineName
--		MULTIMEDIA-SYSTEM-CONTROL.ConferenceRequest.requestTerminalCertificate
--		"EM_requestTerminalCertificate">--
--<OSS.FIELDNAME
--		MULTIMEDIA-SYSTEM-CONTROL.ConferenceRequest.requestTerminalCertificate.terminalLabel
--		"terminalLabel">--
--<OSS.DefineName
--		MULTIMEDIA-SYSTEM-CONTROL.ConferenceRequest.requestTerminalCertificate.terminalLabel
--		"EM_RequestTerminalCertificate_terminalLabel">--
--<OSS.FIELDNAME
--		MULTIMEDIA-SYSTEM-CONTROL.ConferenceRequest.requestTerminalCertificate.certSelectionCriteria
--		"certSelectionCriteria">--
--<OSS.DefineName
--		MULTIMEDIA-SYSTEM-CONTROL.ConferenceRequest.requestTerminalCertificate.certSelectionCriteria
--		"EM_certSelectionCriteria">--
--<OSS.FIELDNAME
--		MULTIMEDIA-SYSTEM-CONTROL.ConferenceRequest.requestTerminalCertificate.sRandom
--		"sRandom">--
--<OSS.DefineName
--		MULTIMEDIA-SYSTEM-CONTROL.ConferenceRequest.requestTerminalCertificate.sRandom
--		"EM_sRandom">--
--<OSS.FIELDNAME
--		MULTIMEDIA-SYSTEM-CONTROL.ConferenceRequest.broadcastMyLogicalChannel
--		"broadcastMyLogicalChannel">--
--<OSS.DefineName
--		MULTIMEDIA-SYSTEM-CONTROL.ConferenceRequest.broadcastMyLogicalChannel
--		"EM_ConferenceRequest_broadcastMyLogicalChannel">--
--<OSS.FIELDNAME
--		MULTIMEDIA-SYSTEM-CONTROL.ConferenceRequest.makeTerminalBroadcaster
--		"makeTerminalBroadcaster">--
--<OSS.DefineName
--		MULTIMEDIA-SYSTEM-CONTROL.ConferenceRequest.makeTerminalBroadcaster
--		"EM_ConferenceRequest_makeTerminalBroadcaster">--
--<OSS.FIELDNAME
--		MULTIMEDIA-SYSTEM-CONTROL.ConferenceRequest.sendThisSource
--		"sendThisSource">--
--<OSS.DefineName
--		MULTIMEDIA-SYSTEM-CONTROL.ConferenceRequest.sendThisSource
--		"EM_ConferenceRequest_sendThisSource">--
--<OSS.FIELDNAME
--		MULTIMEDIA-SYSTEM-CONTROL.ConferenceRequest.requestAllTerminalIDs
--		"requestAllTerminalIDs">--
--<OSS.DefineName
--		MULTIMEDIA-SYSTEM-CONTROL.ConferenceRequest.requestAllTerminalIDs
--		"EM_requestAllTerminalIDs">--
--<OSS.FIELDNAME
--		MULTIMEDIA-SYSTEM-CONTROL.ConferenceRequest.remoteMCRequest
--		"remoteMCRequest">--
--<OSS.DefineName
--		MULTIMEDIA-SYSTEM-CONTROL.ConferenceRequest.remoteMCRequest
--		"EM_remoteMCRequest">--
 
-- -------------------------------------------------------------- --
--
-- CertSelectionCriteria ::= SEQUENCE SIZE (1..16) OF Criteria
--
-- -------------------------------------------------------------- --

--<ASN1.PDU
--		MULTIMEDIA-SYSTEM-CONTROL.CertSelectionCriteria>--
--<OSS.TYPENAME
--		MULTIMEDIA-SYSTEM-CONTROL.CertSelectionCriteria
--		"EmCertSelectionCriteria">--

-- -------------------------------------------------------------- --
--
-- Criteria ::= SEQUENCE
-- {
--     field       OBJECT IDENTIFIER,
--     value       OCTET STRING (SIZE(1..65535)),
--     ...
-- }
--
-- -------------------------------------------------------------- --

--<ASN1.PDU
--		MULTIMEDIA-SYSTEM-CONTROL.Criteria>--
--<OSS.TYPENAME
--		MULTIMEDIA-SYSTEM-CONTROL.Criteria
--		"EmCriteria">--
--<OSS.FIELDNAME
--		MULTIMEDIA-SYSTEM-CONTROL.Criteria.field
--		"field">--
--<OSS.UNBOUNDED
--		MULTIMEDIA-SYSTEM-CONTROL.Criteria.value>--
--<OSS.ExtractType
--		MULTIMEDIA-SYSTEM-CONTROL.Criteria.value>--
--<OSS.TYPENAME
--		MULTIMEDIA-SYSTEM-CONTROL.Criteria.value
--		"EmOctetString">--
--<OSS.FIELDNAME
--		MULTIMEDIA-SYSTEM-CONTROL.Criteria.value
--		"value">--

-- -------------------------------------------------------------- --
--  
-- TerminalLabel   ::= SEQUENCE
-- {
--         mcuNumber       McuNumber,
--         terminalNumber  TerminalNumber,
--         ...
-- }
--
-- -------------------------------------------------------------- --

--<ASN1.PDU
--		MULTIMEDIA-SYSTEM-CONTROL.TerminalLabel>--
--<OSS.TYPENAME
--		MULTIMEDIA-SYSTEM-CONTROL.TerminalLabel
--		"EmTerminalLabel">--
--<OSS.FIELDNAME
--		MULTIMEDIA-SYSTEM-CONTROL.TerminalLabel.mcuNumber
--		"mcuNumber">--
--<OSS.FIELDNAME
--		MULTIMEDIA-SYSTEM-CONTROL.TerminalLabel.terminalNumber
--		"terminalNumber">--

-- -------------------------------------------------------------- --
--  
-- McuNumber       ::=INTEGER(0..192)
-- TerminalNumber  ::=INTEGER(0..192)
--
-- -------------------------------------------------------------- --

--<OSS.FIELDNAME
--		MULTIMEDIA-SYSTEM-CONTROL.McuNumber
--		"EmMcuNumber">--
--<OSS.FIELDNAME
--		MULTIMEDIA-SYSTEM-CONTROL.TerminalNumber
--		"EmTerminalNumber">--

-- ==============================================================
-- Conference Response definitions
-- ==============================================================

-- -------------------------------------------------------------- --
--
-- ConferenceResponse  ::= CHOICE
-- {
--     mCTerminalIDResponse    SEQUENCE
--     {
--         terminalLabel   TerminalLabel,
--         terminalID      TerminalID,
--         ...
--     },
--  
--     terminalIDResponse      SEQUENCE
--     {
--         terminalLabel   TerminalLabel,
--         terminalID      TerminalID,
--         ...
--     },
--  
--     conferenceIDResponse    SEQUENCE
--     {
--         terminalLabel   TerminalLabel,
--         conferenceID    ConferenceID,
--         ...
--     },
--  
--     passwordResponse        SEQUENCE
--     {
--         terminalLabel   TerminalLabel,
--         password        Password,
--         ...
--     },
--  
--     terminalListResponse    SET SIZE (1..256) OF TerminalLabel,
--  
--     videoCommandReject      NULL,
--     terminalDropReject      NULL,
--  
--     makeMeChairResponse     CHOICE
--     {
--         grantedChairToken       NULL,
--         deniedChairToken        NULL,
--         ...
--     },
--     ...,
--     extensionAddressResponse    SEQUENCE
--     {
--         extensionAddress    TerminalID,
--         ...
--     },
--     chairTokenOwnerResponse SEQUENCE
--     {
--         terminalLabel   TerminalLabel,
--         terminalID      TerminalID,
--         ...
--     },
--     terminalCertificateResponse     SEQUENCE
--     {
--             terminalLabel               TerminalLabel OPTIONAL,
--             certificateResponse         OCTET STRING (SIZE(1..65535)) OPTIONAL,
--         ...
--     },
--     broadcastMyLogicalChannelResponse   CHOICE
--     {
--         grantedBroadcastMyLogicalChannel    NULL,
--         deniedBroadcastMyLogicalChannel     NULL,
--         ...
--     },
--     makeTerminalBroadcasterResponse CHOICE
--     {
--         grantedMakeTerminalBroadcaster  NULL,
--         deniedMakeTerminalBroadcaster   NULL,
--         ...
--     },
--     sendThisSourceResponse  CHOICE
--     {
--         grantedSendThisSource   NULL,
--         deniedSendThisSource    NULL,
--         ...
--     },
--     requestAllTerminalIDsResponse   RequestAllTerminalIDsResponse,
--     remoteMCResponse                RemoteMCResponse
-- }
--
-- -------------------------------------------------------------- --

--<ASN1.PDU
--		MULTIMEDIA-SYSTEM-CONTROL.ConferenceResponse>--
--<OSS.TYPENAME
--		MULTIMEDIA-SYSTEM-CONTROL.ConferenceResponse
--		"EmConferenceResponse">--
--<OSS.InlineType
--		MULTIMEDIA-SYSTEM-CONTROL.ConferenceResponse.mCTerminalIDResponse>--
--<OSS.TYPENAME
--		MULTIMEDIA-SYSTEM-CONTROL.ConferenceResponse.mCTerminalIDResponse
--		"EmMCTerminalIDResponse">--
--<OSS.FIELDNAME
--		MULTIMEDIA-SYSTEM-CONTROL.ConferenceResponse.mCTerminalIDResponse
--		"mCTerminalIDResponse">--
--<OSS.DefineName
--		MULTIMEDIA-SYSTEM-CONTROL.ConferenceResponse.mCTerminalIDResponse
--		"EM_mCTerminalIDResponse">--
--<OSS.FIELDNAME
--		MULTIMEDIA-SYSTEM-CONTROL.ConferenceResponse.mCTerminalIDResponse.terminalLabel
--		"terminalLabel">--
--<OSS.FIELDNAME
--		MULTIMEDIA-SYSTEM-CONTROL.ConferenceResponse.mCTerminalIDResponse.terminalID
--		"terminalID">--
--<OSS.InlineType
--		MULTIMEDIA-SYSTEM-CONTROL.ConferenceResponse.terminalIDResponse>--
--<OSS.TYPENAME
--		MULTIMEDIA-SYSTEM-CONTROL.ConferenceResponse.terminalIDResponse
--		"EmTerminalIDResponse">--
--<OSS.FIELDNAME
--		MULTIMEDIA-SYSTEM-CONTROL.ConferenceResponse.terminalIDResponse
--		"terminalIDResponse">--
--<OSS.DefineName
--		MULTIMEDIA-SYSTEM-CONTROL.ConferenceResponse.terminalIDResponse
--		"EM_terminalIDResponse">--
--<OSS.FIELDNAME
--		MULTIMEDIA-SYSTEM-CONTROL.ConferenceResponse.terminalIDResponse.terminalLabel
--		"terminalLabel">--
--<OSS.FIELDNAME
--		MULTIMEDIA-SYSTEM-CONTROL.ConferenceResponse.terminalIDResponse.terminalID
--		"terminalID">--
--<OSS.InlineType
--		MULTIMEDIA-SYSTEM-CONTROL.ConferenceResponse.conferenceIDResponse>--
--<OSS.TYPENAME
--		MULTIMEDIA-SYSTEM-CONTROL.ConferenceResponse.conferenceIDResponse
--		"EmConferenceIDResponse">--
--<OSS.FIELDNAME
--		MULTIMEDIA-SYSTEM-CONTROL.ConferenceResponse.conferenceIDResponse
--		"conferenceIDResponse">--
--<OSS.DefineName
--		MULTIMEDIA-SYSTEM-CONTROL.ConferenceResponse.conferenceIDResponse
--		"EM_conferenceIDResponse">--
--<OSS.FIELDNAME
--		MULTIMEDIA-SYSTEM-CONTROL.ConferenceResponse.conferenceIDResponse.terminalLabel
--		"terminalLabel">--
--<OSS.FIELDNAME
--		MULTIMEDIA-SYSTEM-CONTROL.ConferenceResponse.conferenceIDResponse.conferenceID
--		"conferenceID">--
--<OSS.InlineType
--		MULTIMEDIA-SYSTEM-CONTROL.ConferenceResponse.passwordResponse>--
--<OSS.TYPENAME
--		MULTIMEDIA-SYSTEM-CONTROL.ConferenceResponse.passwordResponse
--		"EmPasswordResponse">--
--<OSS.FIELDNAME
--		MULTIMEDIA-SYSTEM-CONTROL.ConferenceResponse.passwordResponse
--		"passwordResponse">--
--<OSS.DefineName
--		MULTIMEDIA-SYSTEM-CONTROL.ConferenceResponse.passwordResponse
--		"EM_passwordResponse">--
--<OSS.FIELDNAME
--		MULTIMEDIA-SYSTEM-CONTROL.ConferenceResponse.passwordResponse.terminalLabel
--		"terminalLabel">--
--<OSS.FIELDNAME
--		MULTIMEDIA-SYSTEM-CONTROL.ConferenceResponse.passwordResponse.password
--		"password">--
--<OSS.FIELDNAME
--		MULTIMEDIA-SYSTEM-CONTROL.ConferenceResponse.terminalListResponse
--		"terminalListResponse">--
--<OSS.DefineName
--		MULTIMEDIA-SYSTEM-CONTROL.ConferenceResponse.terminalListResponse
--		"EM_terminalListResponse">--
--<OSS.FIELDNAME
--		MULTIMEDIA-SYSTEM-CONTROL.ConferenceResponse.videoCommandReject
--		"videoCommandReject">--
--<OSS.DefineName
--		MULTIMEDIA-SYSTEM-CONTROL.ConferenceResponse.videoCommandReject
--		"EM_videoCommandReject">--
--<OSS.FIELDNAME
--		MULTIMEDIA-SYSTEM-CONTROL.ConferenceResponse.terminalDropReject
--		"terminalDropReject">--
--<OSS.DefineName
--		MULTIMEDIA-SYSTEM-CONTROL.ConferenceResponse.terminalDropReject
--		"EM_terminalDropReject">--
--<OSS.ExtractType
--		MULTIMEDIA-SYSTEM-CONTROL.ConferenceResponse.makeMeChairResponse>--
--<OSS.TYPENAME
--		MULTIMEDIA-SYSTEM-CONTROL.ConferenceResponse.makeMeChairResponse
--		"EmMakeMeChairResponse">--
--<OSS.FIELDNAME
--		MULTIMEDIA-SYSTEM-CONTROL.ConferenceResponse.makeMeChairResponse
--		"makeMeChairResponse">--
--<OSS.DefineName
--		MULTIMEDIA-SYSTEM-CONTROL.ConferenceResponse.makeMeChairResponse
--		"EM_makeMeChairResponse">--
--<OSS.FIELDNAME
--		MULTIMEDIA-SYSTEM-CONTROL.ConferenceResponse.makeMeChairResponse.grantedChairToken
--		"grantedChairToken">--
--<OSS.DefineName
--		MULTIMEDIA-SYSTEM-CONTROL.ConferenceResponse.makeMeChairResponse.grantedChairToken
--		"EM_grantedChairToken">--
--<OSS.FIELDNAME
--		MULTIMEDIA-SYSTEM-CONTROL.ConferenceResponse.makeMeChairResponse.deniedChairToken
--		"deniedChairToken">--
--<OSS.DefineName
--		MULTIMEDIA-SYSTEM-CONTROL.ConferenceResponse.makeMeChairResponse.deniedChairToken
--		"EM_deniedChairToken">--
--<OSS.InlineType
--		MULTIMEDIA-SYSTEM-CONTROL.ConferenceResponse.extensionAddressResponse>--
--<OSS.TYPENAME
--		MULTIMEDIA-SYSTEM-CONTROL.ConferenceResponse.extensionAddressResponse
--		"EmExtensionAddressResponse">--
--<OSS.FIELDNAME
--		MULTIMEDIA-SYSTEM-CONTROL.ConferenceResponse.extensionAddressResponse
--		"extensionAddressResponse">--
--<OSS.DefineName
--		MULTIMEDIA-SYSTEM-CONTROL.ConferenceResponse.extensionAddressResponse
--		"EM_extensionAddressResponse">--
--<OSS.InlineType
--		MULTIMEDIA-SYSTEM-CONTROL.ConferenceResponse.chairTokenOwnerResponse>--
--<OSS.TYPENAME
--		MULTIMEDIA-SYSTEM-CONTROL.ConferenceResponse.chairTokenOwnerResponse
--		"EmChairTokenOwnerResponse">--
--<OSS.FIELDNAME
--		MULTIMEDIA-SYSTEM-CONTROL.ConferenceResponse.chairTokenOwnerResponse
--		"chairTokenOwnerResponse">--
--<OSS.DefineName
--		MULTIMEDIA-SYSTEM-CONTROL.ConferenceResponse.chairTokenOwnerResponse
--		"EM_chairTokenOwnerResponse">--
--<OSS.FIELDNAME
--		MULTIMEDIA-SYSTEM-CONTROL.ConferenceResponse.chairTokenOwnerResponse.terminalLabel
--		"terminalLabel">--
--<OSS.FIELDNAME
--		MULTIMEDIA-SYSTEM-CONTROL.ConferenceResponse.chairTokenOwnerResponse.terminalID
--		"terminalID">--
--<OSS.InlineType
--		MULTIMEDIA-SYSTEM-CONTROL.ConferenceResponse.terminalCertificateResponse>--
--<OSS.TYPENAME
--		MULTIMEDIA-SYSTEM-CONTROL.ConferenceResponse.terminalCertificateResponse
--		"EmTerminalCertificateResponse">--
--<OSS.FIELDNAME
--		MULTIMEDIA-SYSTEM-CONTROL.ConferenceResponse.terminalCertificateResponse
--		"terminalCertificateResponse">--
--<OSS.DefineName
--		MULTIMEDIA-SYSTEM-CONTROL.ConferenceResponse.terminalCertificateResponse
--		"EM_terminalCertificateResponse">--
--<OSS.FIELDNAME
--		MULTIMEDIA-SYSTEM-CONTROL.ConferenceResponse.terminalCertificateResponse.terminalLabel
--		"terminalLabel">--
--<OSS.DefineName
--		MULTIMEDIA-SYSTEM-CONTROL.ConferenceResponse.terminalCertificateResponse.terminalLabel
--		"EM_TerminalCertificateResponse_terminalLabel">--
--<OSS.UNBOUNDED
--		MULTIMEDIA-SYSTEM-CONTROL.ConferenceResponse.terminalCertificateResponse.certificateResponse>--
--<OSS.ExtractType
--		MULTIMEDIA-SYSTEM-CONTROL.ConferenceResponse.terminalCertificateResponse.certificateResponse>--
--<OSS.TYPENAME
--		MULTIMEDIA-SYSTEM-CONTROL.ConferenceResponse.terminalCertificateResponse.certificateResponse
--		"EmOctetString">--
--<OSS.FIELDNAME
--		MULTIMEDIA-SYSTEM-CONTROL.ConferenceResponse.terminalCertificateResponse.certificateResponse
--		"certificateResponse">--
--<OSS.DefineName
--		MULTIMEDIA-SYSTEM-CONTROL.ConferenceResponse.terminalCertificateResponse.certificateResponse
--		"EM_certificateResponse">--
--<OSS.ExtractType
--		MULTIMEDIA-SYSTEM-CONTROL.ConferenceResponse.broadcastMyLogicalChannelResponse>--
--<OSS.TYPENAME
--		MULTIMEDIA-SYSTEM-CONTROL.ConferenceResponse.broadcastMyLogicalChannelResponse
--		"EmBroadcastMyLogicalChannelResponse">--
--<OSS.FIELDNAME
--		MULTIMEDIA-SYSTEM-CONTROL.ConferenceResponse.broadcastMyLogicalChannelResponse
--		"broadcastMyLogicalChannelResponse">--
--<OSS.DefineName
--		MULTIMEDIA-SYSTEM-CONTROL.ConferenceResponse.broadcastMyLogicalChannelResponse
--		"EM_broadcastMyLogicalChannelResponse">--
--<OSS.FIELDNAME
--		MULTIMEDIA-SYSTEM-CONTROL.ConferenceResponse.broadcastMyLogicalChannelResponse.grantedBroadcastMyLogicalChannel
--		"grantedBroadcastMyLogicalChannel">--
--<OSS.DefineName
--		MULTIMEDIA-SYSTEM-CONTROL.ConferenceResponse.broadcastMyLogicalChannelResponse.grantedBroadcastMyLogicalChannel
--		"EM_grantedBroadcastMyLogicalChannel">--
--<OSS.FIELDNAME
--		MULTIMEDIA-SYSTEM-CONTROL.ConferenceResponse.broadcastMyLogicalChannelResponse.deniedBroadcastMyLogicalChannel
--		"deniedBroadcastMyLogicalChannel">--
--<OSS.DefineName
--		MULTIMEDIA-SYSTEM-CONTROL.ConferenceResponse.broadcastMyLogicalChannelResponse.deniedBroadcastMyLogicalChannel
--		"EM_deniedBroadcastMyLogicalChannel">--
--<OSS.ExtractType
--		MULTIMEDIA-SYSTEM-CONTROL.ConferenceResponse.makeTerminalBroadcasterResponse>--
--<OSS.TYPENAME
--		MULTIMEDIA-SYSTEM-CONTROL.ConferenceResponse.makeTerminalBroadcasterResponse
--		"EmMakeTerminalBroadcasterResponse">--
--<OSS.FIELDNAME
--		MULTIMEDIA-SYSTEM-CONTROL.ConferenceResponse.makeTerminalBroadcasterResponse
--		"makeTerminalBroadcasterResponse">--
--<OSS.DefineName
--		MULTIMEDIA-SYSTEM-CONTROL.ConferenceResponse.makeTerminalBroadcasterResponse
--		"EM_makeTerminalBroadcasterResponse">--
--<OSS.FIELDNAME
--		MULTIMEDIA-SYSTEM-CONTROL.ConferenceResponse.makeTerminalBroadcasterResponse.grantedMakeTerminalBroadcaster
--		"grantedMakeTerminalBroadcaster">--
--<OSS.DefineName
--		MULTIMEDIA-SYSTEM-CONTROL.ConferenceResponse.makeTerminalBroadcasterResponse.grantedMakeTerminalBroadcaster
--		"EM_grantedMakeTerminalBroadcaster">--
--<OSS.FIELDNAME
--		MULTIMEDIA-SYSTEM-CONTROL.ConferenceResponse.makeTerminalBroadcasterResponse.deniedMakeTerminalBroadcaster
--		"deniedMakeTerminalBroadcaster">--
--<OSS.DefineName
--		MULTIMEDIA-SYSTEM-CONTROL.ConferenceResponse.makeTerminalBroadcasterResponse.deniedMakeTerminalBroadcaster
--		"EM_deniedMakeTerminalBroadcaster">--
--<OSS.ExtractType
--		MULTIMEDIA-SYSTEM-CONTROL.ConferenceResponse.sendThisSourceResponse>--
--<OSS.TYPENAME
--		MULTIMEDIA-SYSTEM-CONTROL.ConferenceResponse.sendThisSourceResponse
--		"EmSendThisSourceResponse">--
--<OSS.FIELDNAME
--		MULTIMEDIA-SYSTEM-CONTROL.ConferenceResponse.sendThisSourceResponse
--		"sendThisSourceResponse">--
--<OSS.DefineName
--		MULTIMEDIA-SYSTEM-CONTROL.ConferenceResponse.sendThisSourceResponse
--		"EM_sendThisSourceResponse">--
--<OSS.FIELDNAME
--		MULTIMEDIA-SYSTEM-CONTROL.ConferenceResponse.sendThisSourceResponse.grantedSendThisSource
--		"grantedSendThisSource">--
--<OSS.DefineName
--		MULTIMEDIA-SYSTEM-CONTROL.ConferenceResponse.sendThisSourceResponse.grantedSendThisSource
--		"EM_grantedSendThisSource">--
--<OSS.FIELDNAME
--		MULTIMEDIA-SYSTEM-CONTROL.ConferenceResponse.sendThisSourceResponse.deniedSendThisSource
--		"deniedSendThisSource">--
--<OSS.DefineName
--		MULTIMEDIA-SYSTEM-CONTROL.ConferenceResponse.sendThisSourceResponse.deniedSendThisSource
--		"EM_deniedSendThisSource">--
--<OSS.FIELDNAME
--		MULTIMEDIA-SYSTEM-CONTROL.ConferenceResponse.requestAllTerminalIDsResponse
--		"requestAllTerminalIDsResponse">--
--<OSS.DefineName
--		MULTIMEDIA-SYSTEM-CONTROL.ConferenceResponse.requestAllTerminalIDsResponse
--		"EM_requestAllTerminalIDsResponse">--
--<OSS.FIELDNAME
--		MULTIMEDIA-SYSTEM-CONTROL.ConferenceResponse.remoteMCResponse
--		"remoteMCResponse">--
--<OSS.DefineName
--		MULTIMEDIA-SYSTEM-CONTROL.ConferenceResponse.remoteMCResponse
--		"EM_remoteMCResponse">--

-- -------------------------------------------------------------- --
--  
-- TerminalID	   ::=OCTET STRING  (SIZE(1..128))
-- ConferenceID    ::=OCTET STRING  (SIZE(1..32))
-- Password        ::=OCTET STRING  (SIZE(1..32))
--
-- -------------------------------------------------------------- --

--<ASN1.PDU
--		MULTIMEDIA-SYSTEM-CONTROL.TerminalID>--
--<OSS.TYPENAME
--		MULTIMEDIA-SYSTEM-CONTROL.TerminalID
--		"EmTerminalID">--
--<ASN1.PDU
--		MULTIMEDIA-SYSTEM-CONTROL.ConferenceID>--
--<OSS.TYPENAME
--		MULTIMEDIA-SYSTEM-CONTROL.ConferenceID
--		"EmConferenceID">--
--<ASN1.PDU
--		MULTIMEDIA-SYSTEM-CONTROL.Password>--
--<OSS.TYPENAME
--		MULTIMEDIA-SYSTEM-CONTROL.Password
--		"EmH245Password">--

-- -------------------------------------------------------------- --
--  
-- RequestAllTerminalIDsResponse ::= SEQUENCE
-- {
--     terminalInformation SEQUENCE OF TerminalInformation,
--     ...
-- }
--
-- -------------------------------------------------------------- --

--<ASN1.PDU
--		MULTIMEDIA-SYSTEM-CONTROL.RequestAllTerminalIDsResponse>--
--<OSS.TYPENAME
--		MULTIMEDIA-SYSTEM-CONTROL.RequestAllTerminalIDsResponse
--		"EmRequestAllTerminalIDsResponse">--
--<OSS.FIELDNAME
--		MULTIMEDIA-SYSTEM-CONTROL.RequestAllTerminalIDsResponse.terminalInformation
--		"terminalInformation">--

-- -------------------------------------------------------------- --
--  
-- TerminalInformation ::= SEQUENCE
-- {
--     terminalLabel   TerminalLabel,
--     terminalID      TerminalID,
--     ...
-- }
--
-- -------------------------------------------------------------- --

--<ASN1.PDU
--		MULTIMEDIA-SYSTEM-CONTROL.TerminalInformation>--
--<OSS.TYPENAME
--		MULTIMEDIA-SYSTEM-CONTROL.TerminalInformation
--		"EmTerminalInformation">--
--<OSS.FIELDNAME
--		MULTIMEDIA-SYSTEM-CONTROL.TerminalInformation.terminalLabel
--		"terminalLabel">--
--<OSS.FIELDNAME
--		MULTIMEDIA-SYSTEM-CONTROL.TerminalInformation.terminalID
--		"terminalID">--

-- ==============================================================
-- Remote MC Request definitions
-- ==============================================================
 
-- -------------------------------------------------------------- --
--
-- RemoteMCRequest ::= CHOICE
-- {
--     masterActivate  NULL,
--     slaveActivate   NULL,
--     deActivate      NULL,
--     ...
-- }
--
-- -------------------------------------------------------------- --
 
--<ASN1.PDU
--		MULTIMEDIA-SYSTEM-CONTROL.RemoteMCRequest>--
--<OSS.TYPENAME
--		MULTIMEDIA-SYSTEM-CONTROL.RemoteMCRequest
--		"EmRemoteMCRequest">--
--<OSS.FIELDNAME
--		MULTIMEDIA-SYSTEM-CONTROL.RemoteMCRequest.masterActivate
--		"masterActivate">--
--<OSS.DefineName
--		MULTIMEDIA-SYSTEM-CONTROL.RemoteMCRequest.masterActivate
--		"EM_masterActivate">--
--<OSS.FIELDNAME
--		MULTIMEDIA-SYSTEM-CONTROL.RemoteMCRequest.slaveActivate
--		"slaveActivate">--
--<OSS.DefineName
--		MULTIMEDIA-SYSTEM-CONTROL.RemoteMCRequest.slaveActivate
--		"EM_slaveActivate">--
--<OSS.FIELDNAME
--		MULTIMEDIA-SYSTEM-CONTROL.RemoteMCRequest.deActivate
--		"deActivate">--
--<OSS.DefineName
--		MULTIMEDIA-SYSTEM-CONTROL.RemoteMCRequest.deActivate
--		"EM_deActivate">--

-- -------------------------------------------------------------- --
--
-- RemoteMCResponse ::= CHOICE
-- {
--     accept  NULL,
--     reject  CHOICE
--     {
--         unspecified             NULL,
--         functionNotSupported    NULL,
--         ...
--     },
--     ...
-- }
--
-- -------------------------------------------------------------- --

--<ASN1.PDU
--		MULTIMEDIA-SYSTEM-CONTROL.RemoteMCResponse>--
--<OSS.TYPENAME
--		MULTIMEDIA-SYSTEM-CONTROL.RemoteMCResponse
--		"EmRemoteMCResponse">--
--<OSS.FIELDNAME
--		MULTIMEDIA-SYSTEM-CONTROL.RemoteMCResponse.accept
--		"accept">--
--<OSS.DefineName
--		MULTIMEDIA-SYSTEM-CONTROL.RemoteMCResponse.accept
--		"EM_accept">--
--<OSS.ExtractType
--		MULTIMEDIA-SYSTEM-CONTROL.RemoteMCResponse.reject>--
--<OSS.TYPENAME
--		MULTIMEDIA-SYSTEM-CONTROL.RemoteMCResponse.reject
--		"EmRemoteMCResponseReject">--
--<OSS.FIELDNAME
--		MULTIMEDIA-SYSTEM-CONTROL.RemoteMCResponse.reject
--		"reject">--
--<OSS.DefineName
--		MULTIMEDIA-SYSTEM-CONTROL.RemoteMCResponse.reject
--		"EM_reject">--
--<OSS.FIELDNAME
--		MULTIMEDIA-SYSTEM-CONTROL.RemoteMCResponse.reject.unspecified
--		"unspecified">--
--<OSS.DefineName
--		MULTIMEDIA-SYSTEM-CONTROL.RemoteMCResponse.reject.unspecified
--		"EM_RemoteMCResponseReject_unspecified">--
--<OSS.FIELDNAME
--		MULTIMEDIA-SYSTEM-CONTROL.RemoteMCResponse.reject.functionNotSupported
--		"functionNotSupported">--
--<OSS.DefineName
--		MULTIMEDIA-SYSTEM-CONTROL.RemoteMCResponse.reject.functionNotSupported
--		"EM_RemoteMCResponseReject_functionNotSupported">--

-- ==============================================================
-- Command Message definitions
-- ==============================================================
 
-- ==============================================================
-- Command Message : Send Terminal Capability Set
-- ==============================================================
 
-- -------------------------------------------------------------- --
--
-- SendTerminalCapabilitySet   ::= CHOICE
-- {
--     specificRequest SEQUENCE
--     {
--         multiplexCapability BOOLEAN,
--  
--         capabilityTableEntryNumbers SET SIZE (1..65535) OF CapabilityTableEntryN
-- umber OPTIONAL,
--  
--         capabilityDescriptorNumbers SET SIZE (1..256) OF CapabilityDescriptorNum
-- ber OPTIONAL,
--         ...
--     },
--     genericRequest  NULL,
--     ...
-- }
--
-- -------------------------------------------------------------- --
 
--<ASN1.PDU
--		MULTIMEDIA-SYSTEM-CONTROL.SendTerminalCapabilitySet>--
--<OSS.TYPENAME
--		MULTIMEDIA-SYSTEM-CONTROL.SendTerminalCapabilitySet
--		"EmSendTerminalCapabilitySet">--
--<OSS.InlineType
--		MULTIMEDIA-SYSTEM-CONTROL.SendTerminalCapabilitySet.specificRequest>--
--<OSS.TYPENAME
--		MULTIMEDIA-SYSTEM-CONTROL.SendTerminalCapabilitySet.specificRequest
--		"EmSpecificRequest">--
--<OSS.FIELDNAME
--		MULTIMEDIA-SYSTEM-CONTROL.SendTerminalCapabilitySet.specificRequest
--		"specificRequest">--
--<OSS.DefineName
--		MULTIMEDIA-SYSTEM-CONTROL.SendTerminalCapabilitySet.specificRequest
--		"EM_specificRequest">--
--<OSS.FIELDNAME
--		MULTIMEDIA-SYSTEM-CONTROL.SendTerminalCapabilitySet.specificRequest.multiplexCapability
--		"multiplexCapability">--
--<OSS.FIELDNAME
--		MULTIMEDIA-SYSTEM-CONTROL.SendTerminalCapabilitySet.specificRequest.capabilityTableEntryNumbers
--		"capabilityTableEntryNumbers">--
--<OSS.DefineName
--		MULTIMEDIA-SYSTEM-CONTROL.SendTerminalCapabilitySet.specificRequest.capabilityTableEntryNumbers
--		"EM_capabilityTableEntryNumbers">--
--<OSS.FIELDNAME
--		MULTIMEDIA-SYSTEM-CONTROL.SendTerminalCapabilitySet.specificRequest.capabilityDescriptorNumbers
--		"capabilityDescriptorNumbers">--
--<OSS.DefineName
--		MULTIMEDIA-SYSTEM-CONTROL.SendTerminalCapabilitySet.specificRequest.capabilityDescriptorNumbers
--		"EM_capabilityDescriptorNumbers">--
--<OSS.FIELDNAME
--		MULTIMEDIA-SYSTEM-CONTROL.SendTerminalCapabilitySet.genericRequest
--		"genericRequest">--
--<OSS.DefineName
--		MULTIMEDIA-SYSTEM-CONTROL.SendTerminalCapabilitySet.genericRequest
--		"EM_genericRequest">--

-- ==============================================================
-- Command Message : Encryption
-- ==============================================================
 
-- -------------------------------------------------------------- --
--
-- EncryptionCommand   ::= CHOICE
-- {
--     encryptionSE            OCTET STRING,
--     encryptionIVRequest     NULL,
--     encryptionAlgorithmID   SEQUENCE
--     {
--         h233AlgorithmIdentifier SequenceNumber,
--         associatedAlgorithm     NonStandardParameter
--     },
--     ...
-- }
--
-- -------------------------------------------------------------- --
 
--<ASN1.PDU
--		MULTIMEDIA-SYSTEM-CONTROL.EncryptionCommand>--
--<OSS.TYPENAME
--		MULTIMEDIA-SYSTEM-CONTROL.EncryptionCommand
--		"EmEncryptionCommand">--
--<OSS.FIELDNAME
--		MULTIMEDIA-SYSTEM-CONTROL.EncryptionCommand.encryptionSE
--		"encryptionSE">--
--<OSS.DefineName
--		MULTIMEDIA-SYSTEM-CONTROL.EncryptionCommand.encryptionSE
--		"EM_encryptionSE">--
--<OSS.FIELDNAME
--		MULTIMEDIA-SYSTEM-CONTROL.EncryptionCommand.encryptionIVRequest
--		"encryptionIVRequest">--
--<OSS.DefineName
--		MULTIMEDIA-SYSTEM-CONTROL.EncryptionCommand.encryptionIVRequest
--		"EM_encryptionIVRequest">--
--<OSS.InlineType
--		MULTIMEDIA-SYSTEM-CONTROL.EncryptionCommand.encryptionAlgorithmID>--
--<OSS.TYPENAME
--		MULTIMEDIA-SYSTEM-CONTROL.EncryptionCommand.encryptionAlgorithmID
--		"EmEncryptionAlgorithmID">--
--<OSS.FIELDNAME
--		MULTIMEDIA-SYSTEM-CONTROL.EncryptionCommand.encryptionAlgorithmID
--		"encryptionAlgorithmID">--
--<OSS.DefineName
--		MULTIMEDIA-SYSTEM-CONTROL.EncryptionCommand.encryptionAlgorithmID
--		"EM_encryptionAlgorithmID">--
--<OSS.FIELDNAME
--		MULTIMEDIA-SYSTEM-CONTROL.EncryptionCommand.encryptionAlgorithmID.h233AlgorithmIdentifier
--		"h233AlgorithmIdentifier">--
--<OSS.FIELDNAME
--		MULTIMEDIA-SYSTEM-CONTROL.EncryptionCommand.encryptionAlgorithmID.associatedAlgorithm
--		"associatedAlgorithm">--

-- ==============================================================
-- Command Message : Flow Control
-- ==============================================================
 
-- -------------------------------------------------------------- --
--
-- FlowControlCommand  ::= SEQUENCE
-- {
--     scope       CHOICE
--     {
--         logicalChannelNumber    LogicalChannelNumber,
--         resourceID              INTEGER (0..65535),
--         wholeMultiplex          NULL
--     },
--     restriction CHOICE
--     {
--         maximumBitRate  INTEGER (0..16777215),
--         noRestriction   NULL
--     },
--     ...
-- }
--
-- -------------------------------------------------------------- --
 
--<ASN1.PDU
--		MULTIMEDIA-SYSTEM-CONTROL.FlowControlCommand>--
--<OSS.TYPENAME
--		MULTIMEDIA-SYSTEM-CONTROL.FlowControlCommand
--		"EmFlowControlCommand">--
--<OSS.ExtractType
--		MULTIMEDIA-SYSTEM-CONTROL.FlowControlCommand.scope>--
--<OSS.TYPENAME
--		MULTIMEDIA-SYSTEM-CONTROL.FlowControlCommand.scope
--		"EmFlowControlCommandScope">--
--<OSS.FIELDNAME
--		MULTIMEDIA-SYSTEM-CONTROL.FlowControlCommand.scope
--		"scope">--
--<OSS.FIELDNAME
--		MULTIMEDIA-SYSTEM-CONTROL.FlowControlCommand.scope.logicalChannelNumber
--		"logicalChannelNumber">--
--<OSS.DefineName
--		MULTIMEDIA-SYSTEM-CONTROL.FlowControlCommand.scope.logicalChannelNumber
--		"EM_FlowControl_logicalChannelNumber">--
--<OSS.FIELDNAME
--		MULTIMEDIA-SYSTEM-CONTROL.FlowControlCommand.scope.resourceID
--		"resourceID">--
--<OSS.DefineName
--		MULTIMEDIA-SYSTEM-CONTROL.FlowControlCommand.scope.resourceID
--		"EM_FlowControl_resourceID">--
--<OSS.FIELDNAME
--		MULTIMEDIA-SYSTEM-CONTROL.FlowControlCommand.scope.wholeMultiplex
--		"wholeMultiplex">--
--<OSS.DefineName
--		MULTIMEDIA-SYSTEM-CONTROL.FlowControlCommand.scope.wholeMultiplex
--		"EM_FlowControl_wholeMultiplex">--
--<OSS.ExtractType
--		MULTIMEDIA-SYSTEM-CONTROL.FlowControlCommand.restriction>--
--<OSS.TYPENAME
--		MULTIMEDIA-SYSTEM-CONTROL.FlowControlCommand.restriction
--		"EmFlowControlCommandRestriction">--
--<OSS.FIELDNAME
--		MULTIMEDIA-SYSTEM-CONTROL.FlowControlCommand.restriction
--		"restriction">--
--<OSS.FIELDNAME
--		MULTIMEDIA-SYSTEM-CONTROL.FlowControlCommand.restriction.maximumBitRate
--		"maximumBitRate">--
--<OSS.DefineName
--		MULTIMEDIA-SYSTEM-CONTROL.FlowControlCommand.restriction.maximumBitRate
--		"EM_maximumBitRate">--
--<OSS.FIELDNAME
--		MULTIMEDIA-SYSTEM-CONTROL.FlowControlCommand.restriction.noRestriction
--		"noRestriction">--
--<OSS.DefineName
--		MULTIMEDIA-SYSTEM-CONTROL.FlowControlCommand.restriction.noRestriction
--		"EM_noRestriction">--

-- ==============================================================
-- Command Message : Change or End Session
-- ==============================================================
 
-- -------------------------------------------------------------- --
--
-- EndSessionCommand   ::= CHOICE
-- {
--     nonStandard NonStandardParameter,
--  
--     disconnect  NULL,
--  
--     gstnOptions CHOICE
--     {
--         telephonyMode   NULL,
--         v8bis           NULL,
--         v34DSVD         NULL,
--         v34DuplexFAX    NULL,
--         v34H324         NULL,
--         ...
--     },
--  
--     ...,
--     isdnOptions CHOICE
--     {
--         telephonyMode   NULL,
--         v140            NULL,
--         terminalOnHold  NULL,
--         ...
--     }
-- }
--
-- -------------------------------------------------------------- --
 
--<ASN1.PDU
--		MULTIMEDIA-SYSTEM-CONTROL.EndSessionCommand>--
--<OSS.TYPENAME
--		MULTIMEDIA-SYSTEM-CONTROL.EndSessionCommand
--		"EmEndSessionCommand">--
--<OSS.FIELDNAME
--		MULTIMEDIA-SYSTEM-CONTROL.EndSessionCommand.nonStandard
--		"nonStandard">--
--<OSS.DefineName
--		MULTIMEDIA-SYSTEM-CONTROL.EndSessionCommand.nonStandard
--		"EM_EndSessionCommand_nonStandard">--
--<OSS.FIELDNAME
--		MULTIMEDIA-SYSTEM-CONTROL.EndSessionCommand.disconnect
--		"disconnect">--
--<OSS.DefineName
--		MULTIMEDIA-SYSTEM-CONTROL.EndSessionCommand.disconnect
--		"EM_disconnect">--
--<OSS.ExtractType
--		MULTIMEDIA-SYSTEM-CONTROL.EndSessionCommand.gstnOptions>--
--<OSS.TYPENAME
--		MULTIMEDIA-SYSTEM-CONTROL.EndSessionCommand.gstnOptions
--		"EmEndSessionCommandGstnOptions">--
--<OSS.FIELDNAME
--		MULTIMEDIA-SYSTEM-CONTROL.EndSessionCommand.gstnOptions
--		"gstnOptions">--
--<OSS.DefineName
--		MULTIMEDIA-SYSTEM-CONTROL.EndSessionCommand.gstnOptions
--		"EM_gstnOptions">--
--<OSS.FIELDNAME
--		MULTIMEDIA-SYSTEM-CONTROL.EndSessionCommand.gstnOptions.telephonyMode
--		"telephonyMode">--
--<OSS.DefineName
--		MULTIMEDIA-SYSTEM-CONTROL.EndSessionCommand.gstnOptions.telephonyMode
--		"EM_GSTN_telephonyMode">--
--<OSS.FIELDNAME
--		MULTIMEDIA-SYSTEM-CONTROL.EndSessionCommand.gstnOptions.v8bis
--		"v8bis">--
--<OSS.DefineName
--		MULTIMEDIA-SYSTEM-CONTROL.EndSessionCommand.gstnOptions.v8bis
--		"EM_v8bis">--
--<OSS.FIELDNAME
--		MULTIMEDIA-SYSTEM-CONTROL.EndSessionCommand.gstnOptions.v34DSVD
--		"v34DSVD">--
--<OSS.DefineName
--		MULTIMEDIA-SYSTEM-CONTROL.EndSessionCommand.gstnOptions.v34DSVD
--		"EM_v34DSVD">--
--<OSS.FIELDNAME
--		MULTIMEDIA-SYSTEM-CONTROL.EndSessionCommand.gstnOptions.v34DuplexFAX
--		"v34DuplexFAX">--
--<OSS.DefineName
--		MULTIMEDIA-SYSTEM-CONTROL.EndSessionCommand.gstnOptions.v34DuplexFAX
--		"EM_v34DuplexFAX">--
--<OSS.FIELDNAME
--		MULTIMEDIA-SYSTEM-CONTROL.EndSessionCommand.gstnOptions.v34H324
--		"v34H324">--
--<OSS.DefineName
--		MULTIMEDIA-SYSTEM-CONTROL.EndSessionCommand.gstnOptions.v34H324
--		"EM_v34H324">--
--<OSS.ExtractType
--		MULTIMEDIA-SYSTEM-CONTROL.EndSessionCommand.isdnOptions>--
--<OSS.TYPENAME
--		MULTIMEDIA-SYSTEM-CONTROL.EndSessionCommand.isdnOptions
--		"EmEndSessionCommandIsdnOptions">--
--<OSS.FIELDNAME
--		MULTIMEDIA-SYSTEM-CONTROL.EndSessionCommand.isdnOptions
--		"isdnOptions">--
--<OSS.DefineName
--		MULTIMEDIA-SYSTEM-CONTROL.EndSessionCommand.isdnOptions
--		"EM_isdnOptions">--
--<OSS.FIELDNAME
--		MULTIMEDIA-SYSTEM-CONTROL.EndSessionCommand.isdnOptions.telephonyMode
--		"telephonyMode">--
--<OSS.DefineName
--		MULTIMEDIA-SYSTEM-CONTROL.EndSessionCommand.isdnOptions.telephonyMode
--		"EM_ISDN_telephonyMode">--
--<OSS.FIELDNAME
--		MULTIMEDIA-SYSTEM-CONTROL.EndSessionCommand.isdnOptions.v140
--		"v140">--
--<OSS.DefineName
--		MULTIMEDIA-SYSTEM-CONTROL.EndSessionCommand.isdnOptions.v140
--		"EM_v140">--
--<OSS.FIELDNAME
--		MULTIMEDIA-SYSTEM-CONTROL.EndSessionCommand.isdnOptions.terminalOnHold
--		"terminalOnHold">--
--<OSS.DefineName
--		MULTIMEDIA-SYSTEM-CONTROL.EndSessionCommand.isdnOptions.terminalOnHold
--		"EM_terminalOnHold">--

-- ==============================================================
-- Command Message : Conference Commands
-- ==============================================================
 
-- -------------------------------------------------------------- --
--
-- ConferenceCommand   ::= CHOICE
-- {
--     broadcastMyLogicalChannel       LogicalChannelNumber,
--     cancelBroadcastMyLogicalChannel LogicalChannelNumber,
--  
--     makeTerminalBroadcaster         TerminalLabel,
--     cancelMakeTerminalBroadcaster   NULL,
--  
--     sendThisSource                  TerminalLabel,
--     cancelSendThisSource            NULL,
--  
--     dropConference                  NULL,
--     ...,
--     substituteConferenceIDCommand   SubstituteConferenceIDCommand
-- }
--
-- -------------------------------------------------------------- --
 
--<ASN1.PDU
--		MULTIMEDIA-SYSTEM-CONTROL.ConferenceCommand>--
--<OSS.TYPENAME
--		MULTIMEDIA-SYSTEM-CONTROL.ConferenceCommand
--		"EmConferenceCommand">--
--<OSS.FIELDNAME
--		MULTIMEDIA-SYSTEM-CONTROL.ConferenceCommand.broadcastMyLogicalChannel
--		"broadcastMyLogicalChannel">--
--<OSS.DefineName
--		MULTIMEDIA-SYSTEM-CONTROL.ConferenceCommand.broadcastMyLogicalChannel
--		"EM_ConferenceCommand_broadcastMyLogicalChannel">--
--<OSS.FIELDNAME
--		MULTIMEDIA-SYSTEM-CONTROL.ConferenceCommand.cancelBroadcastMyLogicalChannel
--		"cancelBroadcastMyLogicalChannel">--
--<OSS.DefineName
--		MULTIMEDIA-SYSTEM-CONTROL.ConferenceCommand.cancelBroadcastMyLogicalChannel
--		"EM_cancelBroadcastMyLogicalChannel">--
--<OSS.FIELDNAME
--		MULTIMEDIA-SYSTEM-CONTROL.ConferenceCommand.makeTerminalBroadcaster
--		"makeTerminalBroadcaster">--
--<OSS.DefineName
--		MULTIMEDIA-SYSTEM-CONTROL.ConferenceCommand.makeTerminalBroadcaster
--		"EM_ConferenceCommand_makeTerminalBroadcaster">--
--<OSS.FIELDNAME
--		MULTIMEDIA-SYSTEM-CONTROL.ConferenceCommand.cancelMakeTerminalBroadcaster
--		"cancelMakeTerminalBroadcaster">--
--<OSS.DefineName
--		MULTIMEDIA-SYSTEM-CONTROL.ConferenceCommand.cancelMakeTerminalBroadcaster
--		"EM_cancelMakeTerminalBroadcaster">--
--<OSS.FIELDNAME
--		MULTIMEDIA-SYSTEM-CONTROL.ConferenceCommand.sendThisSource
--		"sendThisSource">--
--<OSS.DefineName
--		MULTIMEDIA-SYSTEM-CONTROL.ConferenceCommand.sendThisSource
--		"EM_ConferenceCommand_sendThisSource">--
--<OSS.FIELDNAME
--		MULTIMEDIA-SYSTEM-CONTROL.ConferenceCommand.cancelSendThisSource
--		"cancelSendThisSource">--
--<OSS.DefineName
--		MULTIMEDIA-SYSTEM-CONTROL.ConferenceCommand.cancelSendThisSource
--		"EM_cancelSendThisSource">--
--<OSS.FIELDNAME
--		MULTIMEDIA-SYSTEM-CONTROL.ConferenceCommand.dropConference
--		"dropConference">--
--<OSS.DefineName
--		MULTIMEDIA-SYSTEM-CONTROL.ConferenceCommand.dropConference
--		"EM_dropConference">--
--<OSS.FIELDNAME
--		MULTIMEDIA-SYSTEM-CONTROL.ConferenceCommand.substituteConferenceIDCommand
--		"substituteConferenceIDCommand">--
--<OSS.DefineName
--		MULTIMEDIA-SYSTEM-CONTROL.ConferenceCommand.substituteConferenceIDCommand
--		"EM_substituteConferenceIDCommand">--

-- -------------------------------------------------------------- --
--
-- SubstituteConferenceIDCommand ::= SEQUENCE
-- {
--     conferenceIdentifier    OCTET STRING (SIZE(16)),
--     ...
-- }
--
-- -------------------------------------------------------------- --

--<ASN1.PDU
--		MULTIMEDIA-SYSTEM-CONTROL.SubstituteConferenceIDCommand>--
--<OSS.TYPENAME
--		MULTIMEDIA-SYSTEM-CONTROL.SubstituteConferenceIDCommand
--		"EmSubstituteConferenceIDCommand">--
--<OSS.TYPENAME
--		MULTIMEDIA-SYSTEM-CONTROL.SubstituteConferenceIDCommand.conferenceIdentifier
--		"EmH245ConferenceIdentifier">--
--<OSS.FIELDNAME
--		MULTIMEDIA-SYSTEM-CONTROL.SubstituteConferenceIDCommand.conferenceIdentifier
--		"conferenceIdentifier">--

-- ==============================================================
-- Command Message : Miscellaneous H.230-like commands
-- ==============================================================
 
-- -------------------------------------------------------------- --
--
-- MiscellaneousCommand    ::= SEQUENCE
-- {
--     logicalChannelNumber    LogicalChannelNumber,
--     type        CHOICE
--     {
--         equaliseDelay               NULL,
--         zeroDelay                   NULL,
--         multipointModeCommand       NULL,
--         cancelMultipointModeCommand NULL,
--         videoFreezePicture          NULL,
--         videoFastUpdatePicture      NULL,
--  
--         videoFastUpdateGOB  SEQUENCE
--         {
--             firstGOB        INTEGER (0..17),
--             numberOfGOBs    INTEGER (1..18)
--         },
--  
--         videoTemporalSpatialTradeOff    INTEGER (0..31),
--  
--         videoSendSyncEveryGOB       NULL,
--         videoSendSyncEveryGOBCancel NULL,
--  
--         ...,
--         videoFastUpdateMB   SEQUENCE
--         {
--             firstGOB    INTEGER (0..255) OPTIONAL,
--             firstMB     INTEGER (1..8192) OPTIONAL,
--             numberOfMBs INTEGER (1..8192),
--             ...
--         },
--         maxH223MUXPDUsize       INTEGER(1..65535),
--         encryptionUpdate        EncryptionSync,
--         encryptionUpdateRequest EncryptionUpdateRequest,
--         switchReceiveMediaOff   NULL,
--         switchReceiveMediaOn    NULL,
--  
--         progressiveRefinementStart  SEQUENCE
--         {
--             repeatCount CHOICE
--             {
--                 doOneProgression                    NULL,
--                 doContinuousProgressions            NULL,
--                 doOneIndependentProgression         NULL,
--                 doContinuousIndependentProgressions NULL,
--                 ...
--             },
--             ...
--         },
--         progressiveRefinementAbortOne           NULL,
--         progressiveRefinementAbortContinuous    NULL
--  
--     },
--     ...
-- }
--
-- -------------------------------------------------------------- --

--<ASN1.PDU
--		MULTIMEDIA-SYSTEM-CONTROL.MiscellaneousCommand>--
--<OSS.TYPENAME
--		MULTIMEDIA-SYSTEM-CONTROL.MiscellaneousCommand
--		"EmMiscellaneousCommand">--
--<OSS.FIELDNAME
--		MULTIMEDIA-SYSTEM-CONTROL.MiscellaneousCommand.logicalChannelNumber
--		"logicalChannelNumber">--
--<OSS.ExtractType
--		MULTIMEDIA-SYSTEM-CONTROL.MiscellaneousCommand.type>--
--<OSS.TYPENAME
--		MULTIMEDIA-SYSTEM-CONTROL.MiscellaneousCommand.type
--		"EmMiscCommandType">--
--<OSS.FIELDNAME
--		MULTIMEDIA-SYSTEM-CONTROL.MiscellaneousCommand.type
--		"type">--
--<OSS.FIELDNAME
--		MULTIMEDIA-SYSTEM-CONTROL.MiscellaneousCommand.type.equaliseDelay
--		"equaliseDelay">--
--<OSS.DefineName
--		MULTIMEDIA-SYSTEM-CONTROL.MiscellaneousCommand.type.equaliseDelay
--		"EM_equaliseDelay">--
--<OSS.FIELDNAME
--		MULTIMEDIA-SYSTEM-CONTROL.MiscellaneousCommand.type.zeroDelay
--		"zeroDelay">--
--<OSS.DefineName
--		MULTIMEDIA-SYSTEM-CONTROL.MiscellaneousCommand.type.zeroDelay
--		"EM_zeroDelay">--
--<OSS.FIELDNAME
--		MULTIMEDIA-SYSTEM-CONTROL.MiscellaneousCommand.type.multipointModeCommand
--		"multipointModeCommand">--
--<OSS.DefineName
--		MULTIMEDIA-SYSTEM-CONTROL.MiscellaneousCommand.type.multipointModeCommand
--		"EM_multipointModeCommand">--
--<OSS.FIELDNAME
--		MULTIMEDIA-SYSTEM-CONTROL.MiscellaneousCommand.type.cancelMultipointModeCommand
--		"cancelMultipointModeCommand">--
--<OSS.DefineName
--		MULTIMEDIA-SYSTEM-CONTROL.MiscellaneousCommand.type.cancelMultipointModeCommand
--		"EM_cancelMultipointModeCommand">--
--<OSS.FIELDNAME
--		MULTIMEDIA-SYSTEM-CONTROL.MiscellaneousCommand.type.videoFreezePicture
--		"videoFreezePicture">--
--<OSS.DefineName
--		MULTIMEDIA-SYSTEM-CONTROL.MiscellaneousCommand.type.videoFreezePicture
--		"EM_videoFreezePicture">--
--<OSS.FIELDNAME
--		MULTIMEDIA-SYSTEM-CONTROL.MiscellaneousCommand.type.videoFastUpdatePicture
--		"videoFastUpdatePicture">--
--<OSS.DefineName
--		MULTIMEDIA-SYSTEM-CONTROL.MiscellaneousCommand.type.videoFastUpdatePicture
--		"EM_videoFastUpdatePicture">--
--<OSS.InlineType
--		MULTIMEDIA-SYSTEM-CONTROL.MiscellaneousCommand.type.videoFastUpdateGOB>--
--<OSS.TYPENAME
--		MULTIMEDIA-SYSTEM-CONTROL.MiscellaneousCommand.type.videoFastUpdateGOB
--		"EmVideoFastUpdateGOB">--
--<OSS.FIELDNAME
--		MULTIMEDIA-SYSTEM-CONTROL.MiscellaneousCommand.type.videoFastUpdateGOB
--		"videoFastUpdateGOB">--
--<OSS.DefineName
--		MULTIMEDIA-SYSTEM-CONTROL.MiscellaneousCommand.type.videoFastUpdateGOB
--		"EM_videoFastUpdateGOB">--
--<OSS.FIELDNAME
--		MULTIMEDIA-SYSTEM-CONTROL.MiscellaneousCommand.type.videoFastUpdateGOB.firstGOB
--		"firstGOB">--
--<OSS.FIELDNAME
--		MULTIMEDIA-SYSTEM-CONTROL.MiscellaneousCommand.type.videoFastUpdateGOB.numberOfGOBs
--		"numberOfGOBs">--
--<OSS.FIELDNAME
--		MULTIMEDIA-SYSTEM-CONTROL.MiscellaneousCommand.type.videoTemporalSpatialTradeOff
--		"videoTemporalSpatialTradeOff">--
--<OSS.DefineName
--		MULTIMEDIA-SYSTEM-CONTROL.MiscellaneousCommand.type.videoTemporalSpatialTradeOff
--		"EM_MiscCommandType_videoTemporalSpatialTradeOff">--
--<OSS.FIELDNAME
--		MULTIMEDIA-SYSTEM-CONTROL.MiscellaneousCommand.type.videoSendSyncEveryGOB
--		"videoSendSyncEveryGOB">--
--<OSS.DefineName
--		MULTIMEDIA-SYSTEM-CONTROL.MiscellaneousCommand.type.videoSendSyncEveryGOB
--		"EM_videoSendSyncEveryGOB">--
--<OSS.FIELDNAME
--		MULTIMEDIA-SYSTEM-CONTROL.MiscellaneousCommand.type.videoSendSyncEveryGOBCancel
--		"videoSendSyncEveryGOBCancel">--
--<OSS.DefineName
--		MULTIMEDIA-SYSTEM-CONTROL.MiscellaneousCommand.type.videoSendSyncEveryGOBCancel
--		"EM_videoSendSyncEveryGOBCancel">--
--<OSS.InlineType
--		MULTIMEDIA-SYSTEM-CONTROL.MiscellaneousCommand.type.videoFastUpdateMB>--
--<OSS.TYPENAME
--		MULTIMEDIA-SYSTEM-CONTROL.MiscellaneousCommand.type.videoFastUpdateMB
--		"EmVideoFastUpdateMB">--
--<OSS.FIELDNAME
--		MULTIMEDIA-SYSTEM-CONTROL.MiscellaneousCommand.type.videoFastUpdateMB
--		"videoFastUpdateMB">--
--<OSS.DefineName
--		MULTIMEDIA-SYSTEM-CONTROL.MiscellaneousCommand.type.videoFastUpdateMB
--		"EM_videoFastUpdateMB">--
--<OSS.FIELDNAME
--		MULTIMEDIA-SYSTEM-CONTROL.MiscellaneousCommand.type.videoFastUpdateMB.firstGOB
--		"firstGOB">--
--<OSS.DefineName
--		MULTIMEDIA-SYSTEM-CONTROL.MiscellaneousCommand.type.videoFastUpdateMB.firstGOB
--		"EM_firstGOB">--
--<OSS.FIELDNAME
--		MULTIMEDIA-SYSTEM-CONTROL.MiscellaneousCommand.type.videoFastUpdateMB.firstMB
--		"firstMB">--
--<OSS.DefineName
--		MULTIMEDIA-SYSTEM-CONTROL.MiscellaneousCommand.type.videoFastUpdateMB.firstMB
--		"EM_firstMB">--
--<OSS.FIELDNAME
--		MULTIMEDIA-SYSTEM-CONTROL.MiscellaneousCommand.type.videoFastUpdateMB.numberOfMBs
--		"numberOfMBs">--
--<OSS.FIELDNAME
--		MULTIMEDIA-SYSTEM-CONTROL.MiscellaneousCommand.type.maxH223MUXPDUsize
--		"maxH223MUXPDUsize">--
--<OSS.DefineName
--		MULTIMEDIA-SYSTEM-CONTROL.MiscellaneousCommand.type.maxH223MUXPDUsize
--		"EM_maxH223MUXPDUsize">--
--<OSS.FIELDNAME
--		MULTIMEDIA-SYSTEM-CONTROL.MiscellaneousCommand.type.encryptionUpdate
--		"encryptionUpdate">--
--<OSS.DefineName
--		MULTIMEDIA-SYSTEM-CONTROL.MiscellaneousCommand.type.encryptionUpdate
--		"EM_encryptionUpdate">--
--<OSS.FIELDNAME
--		MULTIMEDIA-SYSTEM-CONTROL.MiscellaneousCommand.type.encryptionUpdateRequest
--		"encryptionUpdateRequest">--
--<OSS.DefineName
--		MULTIMEDIA-SYSTEM-CONTROL.MiscellaneousCommand.type.encryptionUpdateRequest
--		"EM_encryptionUpdateRequest">--
--<OSS.FIELDNAME
--		MULTIMEDIA-SYSTEM-CONTROL.MiscellaneousCommand.type.switchReceiveMediaOff
--		"switchReceiveMediaOff">--
--<OSS.DefineName
--		MULTIMEDIA-SYSTEM-CONTROL.MiscellaneousCommand.type.switchReceiveMediaOff
--		"EM_switchReceiveMediaOff">--
--<OSS.FIELDNAME
--		MULTIMEDIA-SYSTEM-CONTROL.MiscellaneousCommand.type.switchReceiveMediaOn
--		"switchReceiveMediaOn">--
--<OSS.DefineName
--		MULTIMEDIA-SYSTEM-CONTROL.MiscellaneousCommand.type.switchReceiveMediaOn
--		"EM_switchReceiveMediaOn">--
--<OSS.InlineType
--		MULTIMEDIA-SYSTEM-CONTROL.MiscellaneousCommand.type.progressiveRefinementStart>--
--<OSS.TYPENAME
--		MULTIMEDIA-SYSTEM-CONTROL.MiscellaneousCommand.type.progressiveRefinementStart
--		"EmProgressiveRefinementStart">--
--<OSS.FIELDNAME
--		MULTIMEDIA-SYSTEM-CONTROL.MiscellaneousCommand.type.progressiveRefinementStart
--		"progressiveRefinementStart">--
--<OSS.DefineName
--		MULTIMEDIA-SYSTEM-CONTROL.MiscellaneousCommand.type.progressiveRefinementStart
--		"EM_progressiveRefinementStart">--
--<OSS.ExtractType
--		MULTIMEDIA-SYSTEM-CONTROL.MiscellaneousCommand.type.progressiveRefinementStart.repeatCount>--
--<OSS.TYPENAME
--		MULTIMEDIA-SYSTEM-CONTROL.MiscellaneousCommand.type.progressiveRefinementStart.repeatCount
--		"EmEmProgressiveRefinementStartRepeatCount">--
--<OSS.FIELDNAME
--		MULTIMEDIA-SYSTEM-CONTROL.MiscellaneousCommand.type.progressiveRefinementStart.repeatCount
--		"repeatCount">--
--<OSS.FIELDNAME
--		MULTIMEDIA-SYSTEM-CONTROL.MiscellaneousCommand.type.progressiveRefinementStart.repeatCount.doOneProgression
--		"doOneProgression">--
--<OSS.DefineName
--		MULTIMEDIA-SYSTEM-CONTROL.MiscellaneousCommand.type.progressiveRefinementStart.repeatCount.doOneProgression
--		"EM_doOneProgression">--
--<OSS.FIELDNAME
--		MULTIMEDIA-SYSTEM-CONTROL.MiscellaneousCommand.type.progressiveRefinementStart.repeatCount.doContinuousProgressions
--		"doContinuousProgressions">--
--<OSS.DefineName
--		MULTIMEDIA-SYSTEM-CONTROL.MiscellaneousCommand.type.progressiveRefinementStart.repeatCount.doContinuousProgressions
--		"EM_doContinuousProgressions">--
--<OSS.FIELDNAME
--		MULTIMEDIA-SYSTEM-CONTROL.MiscellaneousCommand.type.progressiveRefinementStart.repeatCount.doOneIndependentProgression
--		"doOneIndependentProgression">--
--<OSS.DefineName
--		MULTIMEDIA-SYSTEM-CONTROL.MiscellaneousCommand.type.progressiveRefinementStart.repeatCount.doOneIndependentProgression
--		"EM_doOneIndependentProgression">--
--<OSS.FIELDNAME
--		MULTIMEDIA-SYSTEM-CONTROL.MiscellaneousCommand.type.progressiveRefinementStart.repeatCount.doContinuousIndependentProgressions
--		"doContinuousIndependentProgressions">--
--<OSS.DefineName
--		MULTIMEDIA-SYSTEM-CONTROL.MiscellaneousCommand.type.progressiveRefinementStart.repeatCount.doContinuousIndependentProgressions
--		"EM_doContinuousIndependentProgressions">--
--<OSS.FIELDNAME
--		MULTIMEDIA-SYSTEM-CONTROL.MiscellaneousCommand.type.progressiveRefinementAbortOne
--		"progressiveRefinementAbortOne">--
--<OSS.DefineName
--		MULTIMEDIA-SYSTEM-CONTROL.MiscellaneousCommand.type.progressiveRefinementAbortOne
--		"EM_progressiveRefinementAbortOne">--
--<OSS.FIELDNAME
--		MULTIMEDIA-SYSTEM-CONTROL.MiscellaneousCommand.type.progressiveRefinementAbortContinuous
--		"progressiveRefinementAbortContinuous">--
--<OSS.DefineName
--		MULTIMEDIA-SYSTEM-CONTROL.MiscellaneousCommand.type.progressiveRefinementAbortContinuous
--		"EM_progressiveRefinementAbortContinuous">--
 
-- -------------------------------------------------------------- --
--
-- KeyProtectionMethod ::= SEQUENCE
-- {
--     secureChannel       BOOLEAN,
--     sharedSecret        BOOLEAN,
--     certProtectedKey    BOOLEAN,
--     ...
-- }
--
-- -------------------------------------------------------------- --
 
--<ASN1.PDU
--		MULTIMEDIA-SYSTEM-CONTROL.KeyProtectionMethod>--
--<OSS.TYPENAME
--		MULTIMEDIA-SYSTEM-CONTROL.KeyProtectionMethod
--		"EmKeyProtectionMethod">--
--<OSS.FIELDNAME
--		MULTIMEDIA-SYSTEM-CONTROL.KeyProtectionMethod.secureChannel
--		"secureChannel">--
--<OSS.FIELDNAME
--		MULTIMEDIA-SYSTEM-CONTROL.KeyProtectionMethod.sharedSecret
--		"sharedSecret">--
--<OSS.FIELDNAME
--		MULTIMEDIA-SYSTEM-CONTROL.KeyProtectionMethod.certProtectedKey
--		"certProtectedKey">--

-- -------------------------------------------------------------- --
--
-- EncryptionUpdateRequest ::= SEQUENCE
-- {
--     keyProtectionMethod KeyProtectionMethod OPTIONAL,
--     ...
-- }
--
-- -------------------------------------------------------------- --

--<ASN1.PDU
--		MULTIMEDIA-SYSTEM-CONTROL.EncryptionUpdateRequest>--
--<OSS.TYPENAME
--		MULTIMEDIA-SYSTEM-CONTROL.EncryptionUpdateRequest
--		"EmEncryptionUpdateRequest">--
--<OSS.FIELDNAME
--		MULTIMEDIA-SYSTEM-CONTROL.EncryptionUpdateRequest.keyProtectionMethod
--		"keyProtectionMethod">--
--<OSS.DefineName
--		MULTIMEDIA-SYSTEM-CONTROL.EncryptionUpdateRequest.keyProtectionMethod
--		"EM_keyProtectionMethod">--

-- ==============================================================
-- Command Message : H.223 Multiplex Reconfiguration
-- ==============================================================

-- -------------------------------------------------------------- --
--
-- H223MultiplexReconfiguration ::= CHOICE
-- {
--     h223ModeChange  CHOICE
--     {
--         toLevel0                    NULL,
--         toLevel1                    NULL,
--         toLevel2                    NULL,
--         toLevel2withOptionalHeader  NULL,
--         ...
--     },
--  
--     h223AnnexADoubleFlag    CHOICE
--     {
--         start   NULL,
--         stop    NULL,
--         ...
--     },
--  
--     ...
-- }
--
-- -------------------------------------------------------------- --
 
--<OSS.TYPENAME
--		MULTIMEDIA-SYSTEM-CONTROL.H223MultiplexReconfiguration
--		"EmH223MultiplexReconfiguration">--
--<OSS.ExtractType
--		MULTIMEDIA-SYSTEM-CONTROL.H223MultiplexReconfiguration.h223ModeChange>--
--<OSS.TYPENAME
--		MULTIMEDIA-SYSTEM-CONTROL.H223MultiplexReconfiguration.h223ModeChange
--		"EmH223ModeChange">--
--<OSS.FIELDNAME
--		MULTIMEDIA-SYSTEM-CONTROL.H223MultiplexReconfiguration.h223ModeChange
--		"h223ModeChange">--
--<OSS.DefineName
--		MULTIMEDIA-SYSTEM-CONTROL.H223MultiplexReconfiguration.h223ModeChange
--		"EM_h223ModeChange">--
--<OSS.FIELDNAME
--		MULTIMEDIA-SYSTEM-CONTROL.H223MultiplexReconfiguration.h223ModeChange.toLevel0
--		"toLevel0">--
--<OSS.DefineName
--		MULTIMEDIA-SYSTEM-CONTROL.H223MultiplexReconfiguration.h223ModeChange.toLevel0
--		"EM_toLevel0">--
--<OSS.FIELDNAME
--		MULTIMEDIA-SYSTEM-CONTROL.H223MultiplexReconfiguration.h223ModeChange.toLevel1
--		"toLevel1">--
--<OSS.DefineName
--		MULTIMEDIA-SYSTEM-CONTROL.H223MultiplexReconfiguration.h223ModeChange.toLevel1
--		"EM_toLevel1">--
--<OSS.FIELDNAME
--		MULTIMEDIA-SYSTEM-CONTROL.H223MultiplexReconfiguration.h223ModeChange.toLevel2
--		"toLevel2">--
--<OSS.DefineName
--		MULTIMEDIA-SYSTEM-CONTROL.H223MultiplexReconfiguration.h223ModeChange.toLevel2
--		"EM_toLevel2">--
--<OSS.FIELDNAME
--		MULTIMEDIA-SYSTEM-CONTROL.H223MultiplexReconfiguration.h223ModeChange.toLevel2withOptionalHeader
--		"toLevel2withOptionalHeader">--
--<OSS.DefineName
--		MULTIMEDIA-SYSTEM-CONTROL.H223MultiplexReconfiguration.h223ModeChange.toLevel2withOptionalHeader
--		"EM_toLevel2withOptionalHeader">--
--<OSS.ExtractType
--		MULTIMEDIA-SYSTEM-CONTROL.H223MultiplexReconfiguration.h223AnnexADoubleFlag>--
--<OSS.TYPENAME
--		MULTIMEDIA-SYSTEM-CONTROL.H223MultiplexReconfiguration.h223AnnexADoubleFlag
--		"EmH223AnnexADoubleFlag">--
--<OSS.FIELDNAME
--		MULTIMEDIA-SYSTEM-CONTROL.H223MultiplexReconfiguration.h223AnnexADoubleFlag
--		"h223AnnexADoubleFlag">--
--<OSS.DefineName
--		MULTIMEDIA-SYSTEM-CONTROL.H223MultiplexReconfiguration.h223AnnexADoubleFlag
--		"EM_h223AnnexADoubleFlag">--
--<OSS.FIELDNAME
--		MULTIMEDIA-SYSTEM-CONTROL.H223MultiplexReconfiguration.h223AnnexADoubleFlag.start
--		"start">--
--<OSS.DefineName
--		MULTIMEDIA-SYSTEM-CONTROL.H223MultiplexReconfiguration.h223AnnexADoubleFlag.start
--		"EM_start">--
--<OSS.FIELDNAME
--		MULTIMEDIA-SYSTEM-CONTROL.H223MultiplexReconfiguration.h223AnnexADoubleFlag.stop
--		"stop">--
--<OSS.DefineName
--		MULTIMEDIA-SYSTEM-CONTROL.H223MultiplexReconfiguration.h223AnnexADoubleFlag.stop
--		"EM_stop">--


-- ==============================================================
-- Indication Message definitions
-- ==============================================================
 
-- ==============================================================
-- Indication Message : Function not understood
-- ==============================================================
 
-- -------------------------------------------------------------- --
--
-- FunctionNotUnderstood   ::= CHOICE
-- {
--     request RequestMessage,
--     response    ResponseMessage,
--     command CommandMessage
-- }
--
-- -------------------------------------------------------------- --

--<ASN1.PDU
--		MULTIMEDIA-SYSTEM-CONTROL.FunctionNotUnderstood>--
--<OSS.TYPENAME
--		MULTIMEDIA-SYSTEM-CONTROL.FunctionNotUnderstood
--		"EmFunctionNotUnderstood">--
--<OSS.FIELDNAME
--		MULTIMEDIA-SYSTEM-CONTROL.FunctionNotUnderstood.request
--		"request">--
--<OSS.DefineName
--		MULTIMEDIA-SYSTEM-CONTROL.FunctionNotUnderstood.request
--		"EM_FunctionNotUnderstood_request">--
--<OSS.FIELDNAME
--		MULTIMEDIA-SYSTEM-CONTROL.FunctionNotUnderstood.response
--		"response">--
--<OSS.DefineName
--		MULTIMEDIA-SYSTEM-CONTROL.FunctionNotUnderstood.response
--		"EM_FunctionNotUnderstood_response">--
--<OSS.FIELDNAME
--		MULTIMEDIA-SYSTEM-CONTROL.FunctionNotUnderstood.command
--		"command">--
--<OSS.DefineName
--		MULTIMEDIA-SYSTEM-CONTROL.FunctionNotUnderstood.command
--		"EM_FunctionNotUnderstood_command">--

-- ==============================================================
-- Indication Message : Function not Supported
-- ==============================================================
 
-- -------------------------------------------------------------- --
--
-- FunctionNotSupported    ::= SEQUENCE
-- {
--     cause       CHOICE
--     {
--         syntaxError NULL,
--         semanticError   NULL,
--         unknownFunction NULL,
--         ...
--     },
--     returnedFunction    OCTET STRING  OPTIONAL,
--     ...
-- }
--
-- -------------------------------------------------------------- --
 
--<OSS.TYPENAME
--		MULTIMEDIA-SYSTEM-CONTROL.FunctionNotSupported
--		"EmFunctionNotSupported">--
--<OSS.ExtractType
--		MULTIMEDIA-SYSTEM-CONTROL.FunctionNotSupported.cause>--
--<OSS.TYPENAME
--		MULTIMEDIA-SYSTEM-CONTROL.FunctionNotSupported.cause
--		"EmFunctionNotSupportedCause">--
--<OSS.FIELDNAME
--		MULTIMEDIA-SYSTEM-CONTROL.FunctionNotSupported.cause
--		"cause">--
--<OSS.FIELDNAME
--		MULTIMEDIA-SYSTEM-CONTROL.FunctionNotSupported.cause.syntaxError
--		"syntaxError">--
--<OSS.DefineName
--		MULTIMEDIA-SYSTEM-CONTROL.FunctionNotSupported.cause.syntaxError
--		"EM_syntaxError">--
--<OSS.FIELDNAME
--		MULTIMEDIA-SYSTEM-CONTROL.FunctionNotSupported.cause.semanticError
--		"semanticError">--
--<OSS.DefineName
--		MULTIMEDIA-SYSTEM-CONTROL.FunctionNotSupported.cause.semanticError
--		"EM_semanticError">--
--<OSS.FIELDNAME
--		MULTIMEDIA-SYSTEM-CONTROL.FunctionNotSupported.cause.unknownFunction
--		"unknownFunction">--
--<OSS.DefineName
--		MULTIMEDIA-SYSTEM-CONTROL.FunctionNotSupported.cause.unknownFunction
--		"EM_unknownFunction">--
--<OSS.FIELDNAME
--		MULTIMEDIA-SYSTEM-CONTROL.FunctionNotSupported.returnedFunction
--		"returnedFunction">--
--<OSS.DefineName
--		MULTIMEDIA-SYSTEM-CONTROL.FunctionNotSupported.returnedFunction
--		"EM_returnedFunction">--

-- ==============================================================
-- Indication Message : Conference
-- ==============================================================
 
-- -------------------------------------------------------------- --
-- TerminalYouAreSeeingInSubPictureNumber ::= SEQUENCE
-- {
-- 	terminalNumber		TerminalNumber,
-- 	subPictureNumber	INTEGER (0..255),
-- 	...
-- }
-- -------------------------------------------------------------- --

--<ASN1.PDU
--		MULTIMEDIA-SYSTEM-CONTROL.TerminalYouAreSeeingInSubPictureNumber>--
--<OSS.TYPENAME
--		MULTIMEDIA-SYSTEM-CONTROL.TerminalYouAreSeeingInSubPictureNumber
--		"EmTerminalYouAreSeeingInSubPictureNumber">--
--<OSS.FIELDNAME
--		MULTIMEDIA-SYSTEM-CONTROL.TerminalYouAreSeeingInSubPictureNumber.terminalNumber
--		"terminalNumber">--
--<OSS.FIELDNAME
--		MULTIMEDIA-SYSTEM-CONTROL.TerminalYouAreSeeingInSubPictureNumber.subPictureNumber
--		"subPictureNumber">--

-- -------------------------------------------------------------- --
-- VideoIndicateCompose ::= SEQUENCE
-- {
-- 	compositionNumber	INTEGER (0..255),
-- 	...
-- }
-- -------------------------------------------------------------- --

--<ASN1.PDU
--		MULTIMEDIA-SYSTEM-CONTROL.VideoIndicateCompose>--
--<OSS.TYPENAME
--		MULTIMEDIA-SYSTEM-CONTROL.VideoIndicateCompose
--		"EmVideoIndicateCompose">--
--<OSS.FIELDNAME
--		MULTIMEDIA-SYSTEM-CONTROL.VideoIndicateCompose.compositionNumber
--		"compositionNumber">--

-- -------------------------------------------------------------- --
--
-- ConferenceIndication    ::= CHOICE
-- {
--     sbeNumber                       INTEGER (0..9),
--  
--     terminalNumberAssign            TerminalLabel,
--  
--     terminalJoinedConference        TerminalLabel,
--  
--     terminalLeftConference          TerminalLabel,
--  
--     seenByAtLeastOneOther           NULL,
--     cancelSeenByAtLeastOneOther     NULL,
--  
--     seenByAll                       NULL,
--     cancelSeenByAll                 NULL,
--  
--     terminalYouAreSeeing            TerminalLabel,
--  
--     requestForFloor                 NULL,
--  
--     ...,
--     withdrawChairToken              NULL,
--  
--     floorRequested                  TerminalLabel
-- 
-- 	   terminalYouAreSeeingInSubPictureNumber 	TerminalYouAreSeeingInSubPictureNumber,
-- 	
-- 	   videoIndicateCompose 					VideoIndicateCompose
-- }
--
-- -------------------------------------------------------------- --
 
--<ASN1.PDU
--		MULTIMEDIA-SYSTEM-CONTROL.ConferenceIndication>--
--<OSS.TYPENAME
--		MULTIMEDIA-SYSTEM-CONTROL.ConferenceIndication
--		"EmConferenceIndication">--
--<OSS.FIELDNAME
--		MULTIMEDIA-SYSTEM-CONTROL.ConferenceIndication.sbeNumber
--		"sbeNumber">--
--<OSS.DefineName
--		MULTIMEDIA-SYSTEM-CONTROL.ConferenceIndication.sbeNumber
--		"EM_sbeNumber">--
--<OSS.FIELDNAME
--		MULTIMEDIA-SYSTEM-CONTROL.ConferenceIndication.terminalNumberAssign
--		"terminalNumberAssign">--
--<OSS.DefineName
--		MULTIMEDIA-SYSTEM-CONTROL.ConferenceIndication.terminalNumberAssign
--		"EM_terminalNumberAssign">--
--<OSS.FIELDNAME
--		MULTIMEDIA-SYSTEM-CONTROL.ConferenceIndication.terminalJoinedConference
--		"terminalJoinedConference">--
--<OSS.DefineName
--		MULTIMEDIA-SYSTEM-CONTROL.ConferenceIndication.terminalJoinedConference
--		"EM_terminalJoinedConference">--
--<OSS.FIELDNAME
--		MULTIMEDIA-SYSTEM-CONTROL.ConferenceIndication.terminalLeftConference
--		"terminalLeftConference">--
--<OSS.DefineName
--		MULTIMEDIA-SYSTEM-CONTROL.ConferenceIndication.terminalLeftConference
--		"EM_terminalLeftConference">--
--<OSS.FIELDNAME
--		MULTIMEDIA-SYSTEM-CONTROL.ConferenceIndication.seenByAtLeastOneOther
--		"seenByAtLeastOneOther">--
--<OSS.DefineName
--		MULTIMEDIA-SYSTEM-CONTROL.ConferenceIndication.seenByAtLeastOneOther
--		"EM_seenByAtLeastOneOther">--
--<OSS.FIELDNAME
--		MULTIMEDIA-SYSTEM-CONTROL.ConferenceIndication.cancelSeenByAtLeastOneOther
--		"cancelSeenByAtLeastOneOther">--
--<OSS.DefineName
--		MULTIMEDIA-SYSTEM-CONTROL.ConferenceIndication.cancelSeenByAtLeastOneOther
--		"EM_cancelSeenByAtLeastOneOther">--
--<OSS.FIELDNAME
--		MULTIMEDIA-SYSTEM-CONTROL.ConferenceIndication.seenByAll
--		"seenByAll">--
--<OSS.DefineName
--		MULTIMEDIA-SYSTEM-CONTROL.ConferenceIndication.seenByAll
--		"EM_seenByAll">--
--<OSS.FIELDNAME
--		MULTIMEDIA-SYSTEM-CONTROL.ConferenceIndication.cancelSeenByAll
--		"cancelSeenByAll">--
--<OSS.DefineName
--		MULTIMEDIA-SYSTEM-CONTROL.ConferenceIndication.cancelSeenByAll
--		"EM_cancelSeenByAll">--
--<OSS.FIELDNAME
--		MULTIMEDIA-SYSTEM-CONTROL.ConferenceIndication.terminalYouAreSeeing
--		"terminalYouAreSeeing">--
--<OSS.DefineName
--		MULTIMEDIA-SYSTEM-CONTROL.ConferenceIndication.terminalYouAreSeeing
--		"EM_terminalYouAreSeeing">--
--<OSS.FIELDNAME
--		MULTIMEDIA-SYSTEM-CONTROL.ConferenceIndication.requestForFloor
--		"requestForFloor">--
--<OSS.DefineName
--		MULTIMEDIA-SYSTEM-CONTROL.ConferenceIndication.requestForFloor
--		"EM_requestForFloor">--
--<OSS.FIELDNAME
--		MULTIMEDIA-SYSTEM-CONTROL.ConferenceIndication.withdrawChairToken
--		"withdrawChairToken">--
--<OSS.DefineName
--		MULTIMEDIA-SYSTEM-CONTROL.ConferenceIndication.withdrawChairToken
--		"EM_withdrawChairToken">--
--<OSS.FIELDNAME
--		MULTIMEDIA-SYSTEM-CONTROL.ConferenceIndication.floorRequested
--		"floorRequested">--
--<OSS.DefineName
--		MULTIMEDIA-SYSTEM-CONTROL.ConferenceIndication.floorRequested
--		"EM_floorRequested">--
--<OSS.FIELDNAME
--		MULTIMEDIA-SYSTEM-CONTROL.ConferenceIndication.terminalYouAreSeeingInSubPictureNumber
--		"terminalYouAreSeeingInSubPictureNumber">--
--<OSS.DefineName
--		MULTIMEDIA-SYSTEM-CONTROL.ConferenceIndication.terminalYouAreSeeingInSubPictureNumber
--		"EM_terminalYouAreSeeingInSubPictureNumber">--
--<OSS.FIELDNAME
--		MULTIMEDIA-SYSTEM-CONTROL.ConferenceIndication.videoIndicateCompose
--		"videoIndicateCompose">--
--<OSS.DefineName
--		MULTIMEDIA-SYSTEM-CONTROL.ConferenceIndication.videoIndicateCompose
--		"EM_videoIndicateCompose">--

-- ==============================================================
-- Indication Message : Miscellaneous H.230-like indication
-- ==============================================================
 
-- -------------------------------------------------------------- --
--
-- MiscellaneousIndication ::= SEQUENCE
-- {
--     logicalChannelNumber    LogicalChannelNumber,
--     type        CHOICE
--     {
--         logicalChannelActive    NULL,
--         logicalChannelInactive  NULL,
--  
--         multipointConference    NULL,
--         cancelMultipointConference  NULL,
--  
--         multipointZeroComm  NULL,
--         cancelMultipointZeroComm    NULL,
--  
--         multipointSecondaryStatus   NULL,
--         cancelMultipointSecondaryStatus NULL,
--  
--         videoIndicateReadyToActivate    NULL,
--  
--         videoTemporalSpatialTradeOff    INTEGER (0..31),
--  
--         ...,
--  
--         videoNotDecodedMBs  SEQUENCE
--           {
--               firstMB   INTEGER (1..6336),
--               numberOfMBs   INTEGER (1..6336),
--               temporalReference INTEGER (0..255),
--             ...
--           }
--		   transportCapability	TransportCapability
--     },
--     ...
-- }
--
-- -------------------------------------------------------------- --

--<ASN1.PDU
--		MULTIMEDIA-SYSTEM-CONTROL.MiscellaneousIndication>--
--<OSS.TYPENAME
--		MULTIMEDIA-SYSTEM-CONTROL.MiscellaneousIndication
--		"EmMiscellaneousIndication">--
--<OSS.FIELDNAME
--		MULTIMEDIA-SYSTEM-CONTROL.MiscellaneousIndication.logicalChannelNumber
--		"logicalChannelNumber">--
--<OSS.ExtractType
--		MULTIMEDIA-SYSTEM-CONTROL.MiscellaneousIndication.type>--
--<OSS.TYPENAME
--		MULTIMEDIA-SYSTEM-CONTROL.MiscellaneousIndication.type
--		"EmMiscIndicationType">--
--<OSS.FIELDNAME
--		MULTIMEDIA-SYSTEM-CONTROL.MiscellaneousIndication.type
--		"type">--
--<OSS.FIELDNAME
--		MULTIMEDIA-SYSTEM-CONTROL.MiscellaneousIndication.type.logicalChannelActive
--		"logicalChannelActive">--
--<OSS.DefineName
--		MULTIMEDIA-SYSTEM-CONTROL.MiscellaneousIndication.type.logicalChannelActive
--		"EM_logicalChannelActive">--
--<OSS.FIELDNAME
--		MULTIMEDIA-SYSTEM-CONTROL.MiscellaneousIndication.type.logicalChannelInactive
--		"logicalChannelInactive">--
--<OSS.DefineName
--		MULTIMEDIA-SYSTEM-CONTROL.MiscellaneousIndication.type.logicalChannelInactive
--		"EM_logicalChannelInactive">--
--<OSS.FIELDNAME
--		MULTIMEDIA-SYSTEM-CONTROL.MiscellaneousIndication.type.multipointConference
--		"multipointConference">--
--<OSS.DefineName
--		MULTIMEDIA-SYSTEM-CONTROL.MiscellaneousIndication.type.multipointConference
--		"EM_multipointConference">--
--<OSS.FIELDNAME
--		MULTIMEDIA-SYSTEM-CONTROL.MiscellaneousIndication.type.cancelMultipointConference
--		"cancelMultipointConference">--
--<OSS.DefineName
--		MULTIMEDIA-SYSTEM-CONTROL.MiscellaneousIndication.type.cancelMultipointConference
--		"EM_cancelMultipointConference">--
--<OSS.FIELDNAME
--		MULTIMEDIA-SYSTEM-CONTROL.MiscellaneousIndication.type.multipointZeroComm
--		"multipointZeroComm">--
--<OSS.DefineName
--		MULTIMEDIA-SYSTEM-CONTROL.MiscellaneousIndication.type.multipointZeroComm
--		"EM_multipointZeroComm">--
--<OSS.FIELDNAME
--		MULTIMEDIA-SYSTEM-CONTROL.MiscellaneousIndication.type.cancelMultipointZeroComm
--		"cancelMultipointZeroComm">--
--<OSS.DefineName
--		MULTIMEDIA-SYSTEM-CONTROL.MiscellaneousIndication.type.cancelMultipointZeroComm
--		"EM_cancelMultipointZeroComm">--
--<OSS.FIELDNAME
--		MULTIMEDIA-SYSTEM-CONTROL.MiscellaneousIndication.type.multipointSecondaryStatus
--		"multipointSecondaryStatus">--
--<OSS.DefineName
--		MULTIMEDIA-SYSTEM-CONTROL.MiscellaneousIndication.type.multipointSecondaryStatus
--		"EM_multipointSecondaryStatus">--
--<OSS.FIELDNAME
--		MULTIMEDIA-SYSTEM-CONTROL.MiscellaneousIndication.type.cancelMultipointSecondaryStatus
--		"cancelMultipointSecondaryStatus">--
--<OSS.DefineName
--		MULTIMEDIA-SYSTEM-CONTROL.MiscellaneousIndication.type.cancelMultipointSecondaryStatus
--		"EM_cancelMultipointSecondaryStatus">--
--<OSS.FIELDNAME
--		MULTIMEDIA-SYSTEM-CONTROL.MiscellaneousIndication.type.videoIndicateReadyToActivate
--		"videoIndicateReadyToActivate">--
--<OSS.DefineName
--		MULTIMEDIA-SYSTEM-CONTROL.MiscellaneousIndication.type.videoIndicateReadyToActivate
--		"EM_videoIndicateReadyToActivate">--
--<OSS.FIELDNAME
--		MULTIMEDIA-SYSTEM-CONTROL.MiscellaneousIndication.type.videoTemporalSpatialTradeOff
--		"videoTemporalSpatialTradeOff">--
--<OSS.DefineName
--		MULTIMEDIA-SYSTEM-CONTROL.MiscellaneousIndication.type.videoTemporalSpatialTradeOff
--		"EM_MiscIndicationType_videoTemporalSpatialTradeOff">--
--<OSS.InlineType
--		MULTIMEDIA-SYSTEM-CONTROL.MiscellaneousIndication.type.videoNotDecodedMBs>--
--<OSS.TYPENAME
--		MULTIMEDIA-SYSTEM-CONTROL.MiscellaneousIndication.type.videoNotDecodedMBs
--		"EmVideoNotDecodedMBs">--
--<OSS.FIELDNAME
--		MULTIMEDIA-SYSTEM-CONTROL.MiscellaneousIndication.type.videoNotDecodedMBs
--		"videoNotDecodedMBs">--
--<OSS.DefineName
--		MULTIMEDIA-SYSTEM-CONTROL.MiscellaneousIndication.type.videoNotDecodedMBs
--		"EM_videoNotDecodedMBs">--
--<OSS.FIELDNAME
--		MULTIMEDIA-SYSTEM-CONTROL.MiscellaneousIndication.type.videoNotDecodedMBs.firstMB
--		"firstMB">--
--<OSS.FIELDNAME
--		MULTIMEDIA-SYSTEM-CONTROL.MiscellaneousIndication.type.videoNotDecodedMBs.numberOfMBs
--		"numberOfMBs">--
--<OSS.FIELDNAME
--		MULTIMEDIA-SYSTEM-CONTROL.MiscellaneousIndication.type.videoNotDecodedMBs.temporalReference
--		"temporalReference">--
--<OSS.FIELDNAME
--		MULTIMEDIA-SYSTEM-CONTROL.MiscellaneousIndication.type.transportCapability
--		"transportCapability">--
--<OSS.DefineName
--		MULTIMEDIA-SYSTEM-CONTROL.MiscellaneousIndication.type.transportCapability
--		"EM_transportCapability">--

-- ==============================================================
-- Indication Message : Jitter Indication
-- ==============================================================
 
-- -------------------------------------------------------------- --
--
-- JitterIndication    ::= SEQUENCE
-- {
--     scope       CHOICE
--     {
--         logicalChannelNumber    LogicalChannelNumber,
--         resourceID  INTEGER (0..65535),
--         wholeMultiplex  NULL
--     },
--     estimatedReceivedJitterMantissa INTEGER (0..3),
--     estimatedReceivedJitterExponent INTEGER (0..7),
--     skippedFrameCount   INTEGER (0..15)  OPTIONAL,
--     additionalDecoderBuffer INTEGER (0..262143)  OPTIONAL,
--     ...
-- }
--
-- -------------------------------------------------------------- --
 
--<ASN1.PDU
--		MULTIMEDIA-SYSTEM-CONTROL.JitterIndication>--
--<OSS.TYPENAME
--		MULTIMEDIA-SYSTEM-CONTROL.JitterIndication
--		"EmJitterIndication">--
--<OSS.ExtractType
--		MULTIMEDIA-SYSTEM-CONTROL.JitterIndication.scope>--
--<OSS.TYPENAME
--		MULTIMEDIA-SYSTEM-CONTROL.JitterIndication.scope
--		"EmJitterIndicationScope">--
--<OSS.FIELDNAME
--		MULTIMEDIA-SYSTEM-CONTROL.JitterIndication.scope
--		"scope">--
--<OSS.FIELDNAME
--		MULTIMEDIA-SYSTEM-CONTROL.JitterIndication.scope.logicalChannelNumber
--		"logicalChannelNumber">--
--<OSS.DefineName
--		MULTIMEDIA-SYSTEM-CONTROL.JitterIndication.scope.logicalChannelNumber
--		"EM_Jitter_logicalChannelNumber">--
--<OSS.FIELDNAME
--		MULTIMEDIA-SYSTEM-CONTROL.JitterIndication.scope.resourceID
--		"resourceID">--
--<OSS.DefineName
--		MULTIMEDIA-SYSTEM-CONTROL.JitterIndication.scope.resourceID
--		"EM_Jitter_resourceID">--
--<OSS.FIELDNAME
--		MULTIMEDIA-SYSTEM-CONTROL.JitterIndication.scope.wholeMultiplex
--		"wholeMultiplex">--
--<OSS.DefineName
--		MULTIMEDIA-SYSTEM-CONTROL.JitterIndication.scope.wholeMultiplex
--		"EM_Jitter_wholeMultiplex">--
--<OSS.FIELDNAME
--		MULTIMEDIA-SYSTEM-CONTROL.JitterIndication.estimatedReceivedJitterMantissa
--		"estimatedReceivedJitterMantissa">--
--<OSS.FIELDNAME
--		MULTIMEDIA-SYSTEM-CONTROL.JitterIndication.estimatedReceivedJitterExponent
--		"estimatedReceivedJitterExponent">--
--<OSS.FIELDNAME
--		MULTIMEDIA-SYSTEM-CONTROL.JitterIndication.skippedFrameCount
--		"skippedFrameCount">--
--<OSS.DefineName
--		MULTIMEDIA-SYSTEM-CONTROL.JitterIndication.skippedFrameCount
--		"EM_skippedFrameCount">--
--<OSS.FIELDNAME
--		MULTIMEDIA-SYSTEM-CONTROL.JitterIndication.additionalDecoderBuffer
--		"additionalDecoderBuffer">--
--<OSS.DefineName
--		MULTIMEDIA-SYSTEM-CONTROL.JitterIndication.additionalDecoderBuffer
--		"EM_additionalDecoderBuffer">--

-- ==============================================================
-- Indication Message : H.223 logical channel skew
-- ==============================================================
 
-- -------------------------------------------------------------- --
--
-- H223SkewIndication  ::= SEQUENCE
-- {
--     logicalChannelNumber1   LogicalChannelNumber,
--     logicalChannelNumber2   LogicalChannelNumber,
--     skew        INTEGER (0..4095),
--     ...
-- }
--
-- -------------------------------------------------------------- --

--<ASN1.Remove
--		MULTIMEDIA-SYSTEM-CONTROL.H223SkewIndication>--
 
-- ==============================================================
-- Indication Message : H.225.0 maximum logical channel skew
-- ==============================================================
 
-- -------------------------------------------------------------- --
--
-- H2250MaximumSkewIndication  ::= SEQUENCE
-- {
--     logicalChannelNumber1   LogicalChannelNumber,
--     logicalChannelNumber2   LogicalChannelNumber,
--     maximumSkew INTEGER (0..4095),
--     ...
-- }
--
-- -------------------------------------------------------------- --
 
--<ASN1.PDU
--		MULTIMEDIA-SYSTEM-CONTROL.H2250MaximumSkewIndication>--
--<OSS.TYPENAME
--		MULTIMEDIA-SYSTEM-CONTROL.H2250MaximumSkewIndication
--		"EmH2250MaximumSkewIndication">--
--<OSS.FIELDNAME
--		MULTIMEDIA-SYSTEM-CONTROL.H2250MaximumSkewIndication.logicalChannelNumber1
--		"logicalChannelNumber1">--
--<OSS.FIELDNAME
--		MULTIMEDIA-SYSTEM-CONTROL.H2250MaximumSkewIndication.logicalChannelNumber2
--		"logicalChannelNumber2">--
--<OSS.FIELDNAME
--		MULTIMEDIA-SYSTEM-CONTROL.H2250MaximumSkewIndication.maximumSkew
--		"maximumSkew">--

-- ==============================================================
-- Indication Message : MC Location Indication
-- ==============================================================
 
-- -------------------------------------------------------------- --
--
-- MCLocationIndication    ::= SEQUENCE
-- {
--     signalAddress   TransportAddress,
--     ...
-- }
--
-- -------------------------------------------------------------- --
 
--<ASN1.PDU
--		MULTIMEDIA-SYSTEM-CONTROL.MCLocationIndication>--
--<OSS.TYPENAME
--		MULTIMEDIA-SYSTEM-CONTROL.MCLocationIndication
--		"EmMCLocationIndication">--
--<OSS.FIELDNAME
--		MULTIMEDIA-SYSTEM-CONTROL.MCLocationIndication.signalAddress
--		"signalAddress">--

-- ==============================================================
-- Indication Message : Vendor Identification
-- ==============================================================
 
-- -------------------------------------------------------------- --
--
-- VendorIdentification        ::= SEQUENCE
-- {
--     vendor              NonStandardIdentifier,
--     productNumber       OCTET STRING (SIZE(1..256))  OPTIONAL,
--     versionNumber       OCTET STRING (SIZE(1..256))  OPTIONAL,
--     ...
-- }
--
-- -------------------------------------------------------------- --
 
--<ASN1.PDU
--		MULTIMEDIA-SYSTEM-CONTROL.VendorIdentification>--
--<OSS.TYPENAME
--		MULTIMEDIA-SYSTEM-CONTROL.VendorIdentification
--		"EmVendorIdentification">--
--<OSS.FIELDNAME
--		MULTIMEDIA-SYSTEM-CONTROL.VendorIdentification.vendor
--		"vendor">--
--<OSS.InlineType
--		MULTIMEDIA-SYSTEM-CONTROL.VendorIdentification.productNumber>--
--<OSS.TYPENAME
--		MULTIMEDIA-SYSTEM-CONTROL.VendorIdentification.productNumber
--		"EmProductNumber">--
--<OSS.FIELDNAME
--		MULTIMEDIA-SYSTEM-CONTROL.VendorIdentification.productNumber
--		"productNumber">--
--<OSS.DefineName
--		MULTIMEDIA-SYSTEM-CONTROL.VendorIdentification.productNumber
--		"EM_productNumber">--
--<OSS.InlineType
--		MULTIMEDIA-SYSTEM-CONTROL.VendorIdentification.versionNumber>--
--<OSS.TYPENAME
--		MULTIMEDIA-SYSTEM-CONTROL.VendorIdentification.versionNumber
--		"versionNumber">--
--<OSS.FIELDNAME
--		MULTIMEDIA-SYSTEM-CONTROL.VendorIdentification.versionNumber
--		"versionNumber">--
--<OSS.DefineName
--		MULTIMEDIA-SYSTEM-CONTROL.VendorIdentification.versionNumber
--		"EM_versionNumber">--

-- ==============================================================
-- Indication Message : New ATM virtual channel indication 
-- ==============================================================
 
-- -------------------------------------------------------------- --
--
-- NewATMVCIndication  ::= SEQUENCE
-- {
--     resourceID  INTEGER(0..65535),
--     bitRate INTEGER(1..65535),
--     bitRateLockedToPCRClock BOOLEAN,
--     bitRateLockedToNetworkClock BOOLEAN,
--     aal         CHOICE
--     {
--         aal1    SEQUENCE
--         {
--             clockRecovery   CHOICE
--             {
--                 nullClockRecovery   NULL,
--                 srtsClockRecovery   NULL,
--                 adaptiveClockRecovery   NULL,
--                 ...
--             },
--             errorCorrection CHOICE
--             {
--                 nullErrorCorrection NULL,
--                 longInterleaver NULL,
--                 shortInterleaver    NULL,
--                 errorCorrectionOnly NULL,
--                 ...
--             },
--             structuredDataTransfer  BOOLEAN,
--             partiallyFilledCells    BOOLEAN,
--             ...
--         },
--         aal5    SEQUENCE
--         {
--             forwardMaximumSDUSize   INTEGER (0..65535),
--             backwardMaximumSDUSize  INTEGER (0..65535),
--             ...
--         },
--         ...
--     },
--     multiplex   CHOICE
--     {
--         noMultiplex NULL,
--         transportStream NULL,
--         programStream   NULL,
--         ...
--     },
--     ...,
--     reverseParameters   SEQUENCE
--     {
--         bitRate                     INTEGER(1..65535),
--         bitRateLockedToPCRClock     BOOLEAN,
--         bitRateLockedToNetworkClock BOOLEAN,
--         multiplex   CHOICE
--         {
--             noMultiplex     NULL,
--             transportStream NULL,
--             programStream   NULL,
--             ...
--         },
--         ...
--     }
-- }
--
-- -------------------------------------------------------------- --

--<ASN1.Remove
--		MULTIMEDIA-SYSTEM-CONTROL.NewATMVCIndication>--
 
-- ==============================================================
-- Indication Message : user input
-- ==============================================================
 
-- -------------------------------------------------------------- --
--
-- UserInputIndication ::= CHOICE
-- {
--     nonStandard NonStandardParameter,
--     alphanumeric    GeneralString,
--     ...,
--     userInputSupportIndication  CHOICE
--     {
--         nonStandard     NonStandardParameter,
--         basicString     NULL,
--         iA5String       NULL,
--         generalString   NULL,
--         ...
--     },
--     signal          SEQUENCE
--     {
--         signalType  IA5String (SIZE (1) ^ FROM ("0123456789#*ABCD!")),
--         duration    INTEGER (1..65535) OPTIONAL,
--         rtp         SEQUENCE
--         {
--             timestamp               INTEGER (0..4294967295) OPTIONAL,
--             expirationTime          INTEGER (0..4294967295) OPTIONAL,
--             logicalChannelNumber    LogicalChannelNumber,
--             ...
--         } OPTIONAL,
--         ...
--     },
--     signalUpdate    SEQUENCE
--     {
--         duration    INTEGER (1..65535),
--         rtp         SEQUENCE
--         {
--             logicalChannelNumber    LogicalChannelNumber,
--             ...
--         } OPTIONAL,
--         ...
--     }
-- }
--
-- -------------------------------------------------------------- --

--<ASN1.PDU
--		MULTIMEDIA-SYSTEM-CONTROL.UserInputIndication>--
--<OSS.TYPENAME
--		MULTIMEDIA-SYSTEM-CONTROL.UserInputIndication
--		"EmUserInputIndication">--
--<OSS.FIELDNAME
--		MULTIMEDIA-SYSTEM-CONTROL.UserInputIndication.nonStandard
--		"nonStandard">--
--<OSS.DefineName
--		MULTIMEDIA-SYSTEM-CONTROL.UserInputIndication.nonStandard
--		"EM_UserInputIndication_nonStandard">--
--<OSS.FIELDNAME
--		MULTIMEDIA-SYSTEM-CONTROL.UserInputIndication.alphanumeric
--		"alphanumeric">--
--<OSS.DefineName
--		MULTIMEDIA-SYSTEM-CONTROL.UserInputIndication.alphanumeric
--		"EM_alphanumeric">--
--<OSS.POINTER 
--		MULTIMEDIA-SYSTEM-CONTROL.UserInputIndication.alphanumeric>--
--<OSS.ExtractType
--		MULTIMEDIA-SYSTEM-CONTROL.UserInputIndication.userInputSupportIndication>--
--<OSS.TYPENAME
--		MULTIMEDIA-SYSTEM-CONTROL.UserInputIndication.userInputSupportIndication
--		"EmUserInputSupportIndication">--
--<OSS.FIELDNAME
--		MULTIMEDIA-SYSTEM-CONTROL.UserInputIndication.userInputSupportIndication
--		"userInputSupportIndication">--
--<OSS.DefineName
--		MULTIMEDIA-SYSTEM-CONTROL.UserInputIndication.userInputSupportIndication
--		"EM_userInputSupportIndication">--
--<OSS.FIELDNAME
--		MULTIMEDIA-SYSTEM-CONTROL.UserInputIndication.userInputSupportIndication.nonStandard
--		"nonStandard">--
--<OSS.DefineName
--		MULTIMEDIA-SYSTEM-CONTROL.UserInputIndication.userInputSupportIndication.nonStandard
--		"EM_UserInputSupportIndication_nonStandard">--
--<OSS.FIELDNAME
--		MULTIMEDIA-SYSTEM-CONTROL.UserInputIndication.userInputSupportIndication.basicString
--		"basicString">--
--<OSS.DefineName
--		MULTIMEDIA-SYSTEM-CONTROL.UserInputIndication.userInputSupportIndication.basicString
--		"EM_UserInputSupportIndication_basicString">--
--<OSS.FIELDNAME
--		MULTIMEDIA-SYSTEM-CONTROL.UserInputIndication.userInputSupportIndication.iA5String
--		"iA5String">--
--<OSS.DefineName
--		MULTIMEDIA-SYSTEM-CONTROL.UserInputIndication.userInputSupportIndication.iA5String
--		"EM_UserInputSupportIndication_iA5String">--
--<OSS.FIELDNAME
--		MULTIMEDIA-SYSTEM-CONTROL.UserInputIndication.userInputSupportIndication.generalString
--		"generalString">--
--<OSS.DefineName
--		MULTIMEDIA-SYSTEM-CONTROL.UserInputIndication.userInputSupportIndication.generalString
--		"EM_UserInputSupportIndication_generalString">--
--<OSS.InlineType
--		MULTIMEDIA-SYSTEM-CONTROL.UserInputIndication.signal>--
--<OSS.TYPENAME
--		MULTIMEDIA-SYSTEM-CONTROL.UserInputIndication.signal
--		"EmSignal">--
--<OSS.FIELDNAME
--		MULTIMEDIA-SYSTEM-CONTROL.UserInputIndication.signal
--		"signal">--
--<OSS.DefineName
--		MULTIMEDIA-SYSTEM-CONTROL.UserInputIndication.signal
--		"EM_signal">--
--<OSS.FIELDNAME
--		MULTIMEDIA-SYSTEM-CONTROL.UserInputIndication.signal.signalType
--		"signalType">--
--<OSS.FIELDNAME
--		MULTIMEDIA-SYSTEM-CONTROL.UserInputIndication.signal.duration
--		"duration">--
--<OSS.DefineName
--		MULTIMEDIA-SYSTEM-CONTROL.UserInputIndication.signal.duration
--		"EM_duration">--
--<OSS.InlineType
--		MULTIMEDIA-SYSTEM-CONTROL.UserInputIndication.signal.rtp>--
--<OSS.TYPENAME
--		MULTIMEDIA-SYSTEM-CONTROL.UserInputIndication.signal.rtp
--		"EmSignalRTP">--
--<OSS.FIELDNAME
--		MULTIMEDIA-SYSTEM-CONTROL.UserInputIndication.signal.rtp
--		"rtp">--
--<OSS.DefineName
--		MULTIMEDIA-SYSTEM-CONTROL.UserInputIndication.signal.rtp
--		"EM_Signal_rtp">--
--<OSS.FIELDNAME
--		MULTIMEDIA-SYSTEM-CONTROL.UserInputIndication.signal.rtp.timestamp
--		"timestamp">--
--<OSS.DefineName
--		MULTIMEDIA-SYSTEM-CONTROL.UserInputIndication.signal.rtp.timestamp
--		"EM_timestamp">--
--<OSS.FIELDNAME
--		MULTIMEDIA-SYSTEM-CONTROL.UserInputIndication.signal.rtp.expirationTime
--		"expirationTime">--
--<OSS.DefineName
--		MULTIMEDIA-SYSTEM-CONTROL.UserInputIndication.signal.rtp.expirationTime
--		"EM_expirationTime">--
--<OSS.FIELDNAME
--		MULTIMEDIA-SYSTEM-CONTROL.UserInputIndication.signal.rtp.logicalChannelNumber
--		"logicalChannelNumber">--
--<OSS.InlineType
--		MULTIMEDIA-SYSTEM-CONTROL.UserInputIndication.signalUpdate>--
--<OSS.TYPENAME
--		MULTIMEDIA-SYSTEM-CONTROL.UserInputIndication.signalUpdate
--		"EmSignalUpdate">--
--<OSS.FIELDNAME
--		MULTIMEDIA-SYSTEM-CONTROL.UserInputIndication.signalUpdate
--		"signalUpdate">--
--<OSS.DefineName
--		MULTIMEDIA-SYSTEM-CONTROL.UserInputIndication.signalUpdate
--		"EM_signalUpdate">--
--<OSS.FIELDNAME
--		MULTIMEDIA-SYSTEM-CONTROL.UserInputIndication.signalUpdate.duration
--		"duration">--
--<OSS.InlineType
--		MULTIMEDIA-SYSTEM-CONTROL.UserInputIndication.signalUpdate.rtp>--
--<OSS.TYPENAME
--		MULTIMEDIA-SYSTEM-CONTROL.UserInputIndication.signalUpdate.rtp
--		"EmSignalUpdateRTP">--
--<OSS.FIELDNAME
--		MULTIMEDIA-SYSTEM-CONTROL.UserInputIndication.signalUpdate.rtp
--		"rtp">--
--<OSS.DefineName
--		MULTIMEDIA-SYSTEM-CONTROL.UserInputIndication.signalUpdate.rtp
--		"EM_SignalUpdate_rtp">--
--<OSS.FIELDNAME
--		MULTIMEDIA-SYSTEM-CONTROL.UserInputIndication.signalUpdate.rtp.logicalChannelNumber
--		"logicalChannelNumber">--
