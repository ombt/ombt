-- SCCS id:	@(#)em_h225anxg.asn	7.1.2.2	01/13/00

ANNEXG-MESSAGES DEFINITIONS AUTOMATIC TAGS ::=
BEGIN

IMPORTS
	AuthenticationMechanism,
	ClearToken,
	CryptoToken,
	TimeStamp,
	OctetString,
	SeqOfCryptoToken
	FROM H235-SECURITY-MESSAGES

	AliasAddress,
	CallIdentifier,
	CryptoH323Token,
	EndpointType,
	GatekeeperIdentifier,
	GloballyUniqueID,
	NonStandardParameter,
	NumberDigits,
	PartyNumber,
	TransportQOS,
	VendorIdentifier,
	IntegrityMechanism,
	ICV,
	ConferenceIdentifier,
	ReleaseCompleteReason,
	TransportAddress,
	ObjectIdentifier,
	SeqOfAliasAddress,
	SeqOfClearToken,
	SeqOfCryptoH323Token,
	SeqOfNonStandardParameter,
	SeqOfObjectIdentifier,
	SeqOfTransportAddress
	FROM H323-MESSAGES;

SeqOfAddressTemplate	::= SEQUENCE OF AddressTemplate
SeqOfAlternateBE		::= SEQUENCE OF AlternateBE
SeqOfUpdateInformation	::= SEQUENCE OF UpdateInformation
SeqOfPriceInfoSpec		::= SEQUENCE OF PriceInfoSpec
SeqOfDescriptorInfo		::= SEQUENCE OF DescriptorInfo
SeqOfDescriptorID		::= SEQUENCE OF DescriptorID
SeqOfContactInformation	::= SEQUENCE OF ContactInformation
SeqOfAccessToken		::= SEQUENCE OF AccessToken
SeqOfRouteInformation	::= SEQUENCE OF RouteInformation
SeqOfUsageField			::= SEQUENCE OF UsageField
SeqOfPriceElement		::= SEQUENCE OF PriceElement
SeqOfSecurityMode		::= SEQUENCE OF SecurityMode
SeqOfPattern			::= SEQUENCE OF Pattern
SeqOfDescriptor			::= SEQUENCE OF Descriptor

Message ::= SEQUENCE
{
	body	AnnexGMessageBody,
	common	AnnexGCommonInfo,
	...
}

AnnexGMessageBody ::= CHOICE
{
	serviceRequest				ServiceRequest,
	serviceConfirmation			ServiceConfirmation,
	serviceRejection			ServiceRejection,
	serviceRelease				ServiceRelease,
	descriptorRequest			DescriptorRequest,
	descriptorConfirmation		DescriptorConfirmation,
	descriptorRejection			DescriptorRejection,
	descriptorIDRequest			DescriptorIDRequest,
	descriptorIDConfirmation	DescriptorIDConfirmation,
	descriptorIDRejection		DescriptorIDRejection,
	descriptorUpdate			DescriptorUpdate,
	descriptorUpdateAck			DescriptorUpdateAck,
	accessRequest				AccessRequest,
	accessConfirmation			AccessConfirmation,
	accessRejection				AccessRejection,
	requestInProgress			RequestInProgress,
	nonStandardRequest			NonStandardRequest,
	nonStandardConfirmation		NonStandardConfirmation,
	nonStandardRejection		NonStandardRejection,
	unknownMessageResponse		UnknownMessageResponse,
	usageRequest				UsageRequest,
	usageConfirmation			UsageConfirmation,
	usageIndication				UsageIndication,
	usageIndicationConfirmation	UsageIndicationConfirmation,
	usageIndicationRejection	UsageIndicationRejection,
	usageRejection				UsageRejection,
	validationRequest			ValidationRequest,
	validationConfirmation		ValidationConfirmation,
	validationRejection			ValidationRejection,
	...
}

AnnexGCommonInfo ::= SEQUENCE
{
	sequenceNumber		INTEGER (0..65535),
	version				AnnexGVersion,
	hopCount			INTEGER (1..255),
	replyAddress		SeqOfTransportAddress OPTIONAL, -- Must be present in request
	integrityCheckValue	ICV OPTIONAL,
	tokens				SeqOfClearToken OPTIONAL,
	cryptoTokens		SeqOfCryptoH323Token OPTIONAL,
	nonStandard			SeqOfNonStandardParameter OPTIONAL,
	...,
	serviceID			ServiceID OPTIONAL
}

--
-- Annex G messages 
--

ServiceRequest ::= SEQUENCE
{
	elementIdentifier	ElementIdentifier OPTIONAL,
	domainIdentifier	AliasAddress OPTIONAL,
	securityMode		SeqOfSecurityMode OPTIONAL,
	timeToLive			INTEGER (1..4294967295) OPTIONAL,
	...
}

SecurityMode ::= SEQUENCE
{
	authentication		AuthenticationMechanism OPTIONAL,
	integrity			IntegrityMechanism OPTIONAL,
	algorithmOIDs		SeqOfObjectIdentifier OPTIONAL,
	...
}

ServiceConfirmation ::= SEQUENCE
{
	elementIdentifier	ElementIdentifier,
	domainIdentifier	AliasAddress,
	alternates			AlternateBEInfo OPTIONAL,
	securityMode		SecurityMode OPTIONAL,
	timeToLive			INTEGER (1..4294967295) OPTIONAL,
	...
}

ServiceRejection ::= SEQUENCE
{
	reason			ServiceRejectionReason,
	alternates		AlternateBEInfo OPTIONAL,
	...
}

ServiceRejectionReason ::= CHOICE
{
	serviceUnavailable	NULL,
	serviceRedirected	NULL,
	security			NULL,
	continue			NULL,
	undefined			NULL,
	...
}

ServiceRelease ::= SEQUENCE
{
	reason			ServiceReleaseReason,
	alternates		AlternateBEInfo OPTIONAL,
	...
}

ServiceReleaseReason ::= CHOICE
{
	outOfService		NULL,
	maintenance			NULL,
	terminated			NULL,
	expired				NULL,
	...
}

DescriptorRequest ::= SEQUENCE
{
	descriptorID	SeqOfDescriptorID,
	...
}

DescriptorConfirmation ::= SEQUENCE
{
	descriptor		SeqOfDescriptor,
	...
}

DescriptorRejection ::= SEQUENCE
{
	reason			DescriptorRejectionReason,
	descriptorID	DescriptorID OPTIONAL,
	...
}

DescriptorRejectionReason ::= CHOICE
{
	packetSizeExceeded		NULL,	-- use other transport type
	illegalID				NULL,	-- no descriptor for provided descriptorID
	security				NULL,	-- request did not meet security requirements
	hopCountExceeded		NULL,
	noServiceRelationship	NULL,
	undefined				NULL,
	...
}

DescriptorIDRequest ::= SEQUENCE
{
	...
}

DescriptorIDConfirmation ::= SEQUENCE
{
	descriptorInfo		SeqOfDescriptorInfo,
	...
}

DescriptorIDRejection ::= SEQUENCE
{
	reason		DescriptorIDRejectionReason,
	...
}

DescriptorIDRejectionReason ::= CHOICE
{
	noDescriptors			NULL,	-- no descriptors to report
	security				NULL,	-- request did not meet security requirements
	hopCountExceeded		NULL,
	noServiceRelationship	NULL,
	undefined				NULL,
	...
}

DescriptorUpdate ::= SEQUENCE
{
	sender			AliasAddress,
	updateInfo		SeqOfUpdateInformation,
	...
}

UpdateInformation ::= SEQUENCE
{
	descriptorInfo	CHOICE
	{
		descriptorID	DescriptorID,
		descriptor		Descriptor,
		...
	},
	updateType	CHOICE
	{
		added		NULL,
		deleted		NULL,
		changed		NULL,
		...
	},
	...
}

DescriptorUpdateAck ::= SEQUENCE
{
	...
}

AccessRequest ::= SEQUENCE
{
	destinationInfo	PartyInformation,
	sourceInfo		PartyInformation OPTIONAL,
	callInfo		CallInformation OPTIONAL,
	usageSpec		UsageSpecification OPTIONAL,
	...
}

AccessConfirmation ::= SEQUENCE
{
	templates		SeqOfAddressTemplate,
	partialResponse	BOOLEAN,
	...
}

AccessRejection ::= SEQUENCE
{
	reason			AccessRejectionReason,
	...
}

AccessRejectionReason ::= CHOICE
{
	noMatch					NULL,	-- no template matched the destinationInfo
	packetSizeExceeded		NULL,	-- use other transport type
	security				NULL,	-- request did not meet security requirements
	hopCountExceeded		NULL,
	needCallInformation		NULL,  	-- Call Information must be specified
	noServiceRelationship	NULL,
	undefined				NULL,
	...
}

UsageRequest ::= SEQUENCE
{
	callInfo	CallInformation,
	usageSpec	UsageSpecification,
	...
}
	
UsageConfirmation ::= SEQUENCE
{
	...
}

UsageRejection ::= SEQUENCE
{
	reason			UsageRejectReason,
	...
}

UsageIndication ::= SEQUENCE
{
	callInfo			CallInformation,
	accessTokens		SeqOfAccessToken OPTIONAL,
	senderRole			Role,
	usageCallStatus		UsageCallStatus,
	srcInfo				PartyInformation OPTIONAL,
	destAddress			PartyInformation,
	startTime			TimeStamp OPTIONAL,
	endTime				TimeStamp OPTIONAL,
	terminationCause	TerminationCause OPTIONAL,
	usageFields			SeqOfUsageField,
	...
}

UsageField ::= SEQUENCE
{
	id				ObjectIdentifier,
	value			OctetString,
	...
}

UsageRejectReason ::= CHOICE
{
	invalidCall				NULL,
	unavailable				NULL,
	security				NULL,
	noServiceRelationship	NULL,
	undefined				NULL,
	...
}

UsageIndicationConfirmation ::= SEQUENCE
{
	...
}

UsageIndicationRejection ::= SEQUENCE
{
	reason			UsageIndicationRejectionReason,
	...
}

UsageIndicationRejectionReason ::= CHOICE
{
	unknownCall				NULL,
	incomplete				NULL,
	security				NULL,
	noServiceRelationship	NULL,
	undefined				NULL,
	...
}

ValidationRequest ::= SEQUENCE
{
	accessToken		SeqOfAccessToken OPTIONAL,
	destinationInfo	PartyInformation OPTIONAL,
	sourceInfo		PartyInformation OPTIONAL,
	callInfo		CallInformation,
	usageSpec		UsageSpecification OPTIONAL,
	...
}

ValidationConfirmation ::= SEQUENCE
{
	destinationInfo	PartyInformation OPTIONAL,
	usageSpec		UsageSpecification OPTIONAL,
	...
}

ValidationRejection ::= SEQUENCE
{
	reason			ValidationRejectionReason,
	...
}

ValidationRejectionReason ::= CHOICE
{
	tokenNotValid			NULL,
	security				NULL,	-- request did not meet security requirements
	hopCountExceeded		NULL,
	missingSorceInfo		NULL,  	
	missingDestInfo			NULL,
	noServiceRelationship	NULL,
	undefined				NULL,
	...
}

RequestInProgress ::= SEQUENCE
{
	delay		INTEGER (1..65535),
	...
}

NonStandardRequest ::= SEQUENCE
{
	...
}

NonStandardConfirmation ::= SEQUENCE
{
	...
}

NonStandardRejection ::= SEQUENCE
{
	reason		NonStandardRejectionReason,
	...
}

NonStandardRejectionReason ::= CHOICE
{
	notSupported			NULL,
	noServiceRelationship	NULL,
	undefined				NULL,
	...
}

UnknownMessageResponse ::= SEQUENCE
{
	unknownMessage		OctetString,
	reason				UnknownMessageReason,
	...
}

UnknownMessageReason ::= CHOICE
{
	notUnderstood		NULL,
	undefined			NULL,
	...
}


--
-- structures common to multiple messages
--

AddressTemplate ::= SEQUENCE
{
	pattern			SeqOfPattern,
	routeInfo		SeqOfRouteInformation,
	timeToLive		INTEGER (1..4294967295),
	...
}

Pattern ::= CHOICE
{
	specific		AliasAddress,
	wildcard		AliasAddress,
	range SEQUENCE
	{
		startOfRange	PartyNumber,
		endOfRange		PartyNumber
	},
	...
}

RouteInformation ::= SEQUENCE
{
	messageType CHOICE
	{
		sendAccessRequest	NULL,
		sendSetup			NULL,
		nonExistent			NULL,
		...
	},
	callSpecific	BOOLEAN,
	usageSpec		UsageSpecification OPTIONAL,
	priceInfo		SeqOfPriceInfoSpec OPTIONAL,
	contacts		SeqOfContactInformation,
	type			EndpointType OPTIONAL,	-- must be present if messageType = sendSetup
	...
}

ContactInformation ::= SEQUENCE
{
	transportAddress	AliasAddress,
	priority			INTEGER (0..127),
	transportQoS		TransportQOS OPTIONAL,
	security			SeqOfSecurityMode OPTIONAL,
	accessTokens		SeqOfAccessToken OPTIONAL,
	...
}

PriceInfoSpec ::= SEQUENCE
{
	currency			Currency,					-- e.g., "USD"
	currencyScale		INTEGER(-127..127),
	validFrom			GlobalTimeStamp OPTIONAL,
	validUntil			GlobalTimeStamp OPTIONAL,
	hoursFrom			TimeString OPTIONAL,		-- "HHMMSS" UTC
	hoursUntil			TimeString OPTIONAL,		-- "HHMMSS" UTC
	priceElement		SeqOfPriceElement OPTIONAL,
	priceFormula		PriceFormula OPTIONAL,
	...
}

PriceElement ::= SEQUENCE
{
	amount				INTEGER(0..4294967295), -- meter increment
	quantum				INTEGER(0..4294967295), -- each or part thereof
	units CHOICE
	{
		seconds			NULL,
		packets			NULL,
		bytes			NULL,
		initial			NULL,
		minimum			NULL,
		maximum			NULL,
		...
	},
	...
}

Descriptor ::= SEQUENCE
{
	descriptorInfo		DescriptorInfo,
	templates			SeqOfAddressTemplate,
	gatekeeperID		GatekeeperIdentifier OPTIONAL,
	...
}

DescriptorInfo ::= SEQUENCE
{
	descriptorID		DescriptorID,
	lastChanged			GlobalTimeStamp,
	...
}


AlternateBEInfo ::= SEQUENCE
{
	alternateBE				SeqOfAlternateBE,
	alternateIsPermanent	BOOLEAN,
	...
}

AlternateBE ::= SEQUENCE
{
	contactAddress		AliasAddress,
	priority			INTEGER (1..127),
	elementIdentifier	ElementIdentifier OPTIONAL,
	...
}

AccessToken ::= CHOICE
{
	token			ClearToken,
	cryptoToken		CryptoH323Token,
	...
}

CallInformation ::= SEQUENCE 
{
	callIdentifier		CallIdentifier,
	conferenceID		ConferenceIdentifier,
	...
}

UsageCallStatus ::= CHOICE
{
	preConnect			NULL,	-- Call has not started
	callInProgress		NULL,	-- Call is in progress
	callEnded			NULL,	-- Call ended
	...,
	registrationLost	NULL	-- Uncertain if call ended or not
}

UserInformation ::= SEQUENCE
{
	userIdentifier		AliasAddress,
	userAuthenticator	SeqOfCryptoH323Token OPTIONAL,
	...
}

UsageSpecification ::= SEQUENCE
{
	sendTo			ElementIdentifier,
	when SEQUENCE
	{
		never		NULL OPTIONAL,
		start		NULL OPTIONAL,
		end			NULL OPTIONAL,
		period		INTEGER(1..65535) OPTIONAL,   -- in seconds
		failures	NULL OPTIONAL,
		...
	},
	required		SeqOfObjectIdentifier,
	preferred		SeqOfObjectIdentifier,
	...
}

PartyInformation ::= SEQUENCE
{
	logicalAddresses	SeqOfAliasAddress,
	domainIdentifier	AliasAddress OPTIONAL,
	transportAddress	AliasAddress OPTIONAL,
	endpointType		EndpointType OPTIONAL,	
	userInfo			UserInformation OPTIONAL,
	timeZone			TimeZone OPTIONAL,
	...
}

Role ::= CHOICE
{
	originator			NULL,
	destination			NULL,
	nonStandardData		NonStandardParameter,
	...
}

TimeZone ::=  INTEGER (-43200..43200) 		-- number of seconds relative to UTC
							-- including DST if appropriate

TerminationCause ::= SEQUENCE
{
	releaseCompleteReason	ReleaseCompleteReason,
	causeIE					INTEGER (1..65535) OPTIONAL,
	nonStandardData			NonStandardParameter OPTIONAL,
	...
}

AnnexGVersion		::=	ObjectIdentifier	
				-- shall be set to  
				-- {itu-t (0) recommendation (0) h(8) 2250 annex (1) g (7) version (0) 1}

DescriptorID		::=	GloballyUniqueID

ServiceID			::=	GloballyUniqueID

ElementIdentifier	::=	BMPString (SIZE(1..128))

GlobalTimeStamp		::=	IA5String (SIZE(14))	-- in the form YYYYMMDDHHmmSS
							-- where YYYY = year, MM = month, DD = day,
							-- HH = hour, mm = minute, SS = second
							-- (for example, 19981219120000 for noon
							-- 19 December 1998)

Currency			::= IA5String (SIZE(3))		-- e.g., "USD"

PriceFormula		::= IA5String (SIZE(1..2048))

TimeString			::= IA5String (SIZE(6))		-- "HHMMSS" UTC

END	-- of ANNEXG-MESSAGES
