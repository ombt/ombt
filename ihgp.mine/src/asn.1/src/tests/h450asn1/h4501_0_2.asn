-- -------------------------------------------------------------------------- --
--
-- H4501-Supplementary-ServiceAPDU-Structure
-- 		Object Id: 0, 0, 8, 450, 1, 0, 2
--
-- -------------------------------------------------------------------------- --

H4501-Supplementary-ServiceAPDU-Structure 		
	{itu-t recommendation h 450 1 version1(0) h4501-facility-information-structure(2)}

DEFINITIONS AUTOMATIC TAGS ::= 
BEGIN

IMPORTS			
	H323CallTransferOperations	FROM Call-Transfer-Operations
		{itu-t recommendation h 450 2 version1(0)  call-transfer-operations(0)} 

	H323CallDiversionOperations FROM Call-Diversion-Operations
	{itu-t recommendation h 450 3 version1(0) call-diversion-operations(0)}

	CallHoldOperations FROM Call-Hold-Operations
	{itu-t recommendation h 450 4 version1(0) call-hold-operations(0)}

	CallParkPickupOperations FROM Call-Park-Pickup-Operations 
	{itu-t recommendation h 450 5 version1(0) call-park-pickup-operations(0)}

	CallWaitingOperations FROM Call-Waiting-Operations
	{itu-t recommendation h 450 6 version1(0)  call-waiting-operations(0)}

	H323-MWI-Operations FROM Message-Waiting-Indication-Operations
	{itu-t recommendation h 450 7 version1(0)  message-waiting-operations(0)} 

 	AliasAddress 				FROM H323-MESSAGES
 	OPERATION, ROS{}, InvokeId 	FROM Remote-Operations-Apdus
 		{itu-t recommendation h 450 1 version1(0) remote-operations-apdus(11)};

H4501SupplementaryService ::= SEQUENCE
{	
	networkFacilityExtension	NetworkFacilityExtension	OPTIONAL,
	interpretationApdu			InterpretationApdu			OPTIONAL,
	serviceApdu					ServiceApdus,
	...
}

NetworkFacilityExtension ::= SEQUENCE  
{	
	sourceEntity				EntityType,
	sourceEntityAddress			AddressInformation		OPTIONAL,
	destinationEntity			EntityType,
	destinationEntityAddress	AddressInformation		OPTIONAL,
	...
}

EntityType ::= CHOICE
{	
	endpoint	NULL, 
	anyEntity	NULL,
	...
} 

AddressInformation ::= AliasAddress
	
InterpretationApdu ::= CHOICE
{ 	
	discardAnyUnrecognizedInvokePdu				NULL,
	clearCallIfAnyInvokePduNotRecognized		NULL,
	rejectAnyUnrecognizedInvokePdu				NULL,
	...
}

RemoteOperationSet ::= ROS{{InvokeIdSet}, {OperationSet}, {OperationSet}}

SeqOfROS ::= SEQUENCE SIZE (1..MAX) OF RemoteOperationSet

ServiceApdus ::= CHOICE
{
	rosApdus	SeqOfROS,  
	... 				
}

InvokeIdSet INTEGER ::= {InvokeIDs,...}

InvokeIDs ::= INTEGER(0..65535)

OperationSet OPERATION ::= 
{
		H323CallTransferOperations
	|	H323CallDiversionOperations
	|	CallHoldOperations
	|	CallParkPickupOperations
	|	CallWaitingOperations
	|	H323-MWI-Operations,
	...
}		
	-- actual values are defined by individual supplementary service 
	-- specifications (e.g. H.450.x or manufacturer specific)

END     -- of H4501- Supplementary-ServiceAPDU-Structure
