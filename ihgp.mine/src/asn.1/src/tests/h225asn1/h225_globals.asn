-- SCCS id:	@(#)h225_globals.asn	7.1.2.1	10/25/99	

-- ------------------------------------------------------------- --
--               Copyright (c) 1996-1998 Lucent Technologies
--                       All Rights Reserved
-- 
--                       THIS IS UNPUBLISHED
--                       PROPRIETARY SOURCE
--                   CODE OF Lucent Technologies
-- 
--           The copyright notice above does not evidence any
--          actual or intended publication of such source code
-- 
--	CVS Information:
--<COMMENT  "$Revision: 1.2 $  $Date: 1998/11/23 21:21:20 $">--
--
--  Filename       :   h225_globals.asn
--  Description    :   This file contains the OSS
--                      ASN.1 compiler directives.
--  Caveats        :   ASN.1 compiler version: 5.0.3
--
--  Revision History
--  Date			Revision description
--  06/04/1998	File Created
--	11/02/1998	Updated to use OSS ASN.1 Tools version 5.0.3.
-- 
-- ------------------------------------------------------------- --

-- ------------------------------------------------------------- --
--
-- Naming conventions
--  
--      Use the convention of using the same names as in the ASN.1 
--		protocol definition where possible. That means all field name 
--		should be the exact same text where possible. This makes 
--		the ITU-T document the documentation for using the structures.
--
--        There are a few exceptions to this name convention:
--
--      - When the '-' char is used in a name, use '_' instead.
--
--      - For structures that do not have names. The ASN.1 compiler
--        tries, for the most part, to duplicate the structure of the
--        ASN.1 definition. This means that inline SEQUENCES in the ASN.1
--		  definition will map to inline structure definitions. Sometimes 
--		  the default behavior of the ASN.1 compiler may be to 'extract' 
--		  the inlined structure.
--        
--        The names of these 'inlined' or 'extracted' structures aren't 
--		  available in the ASN.1 definition. The default compiler's 
--		  behavior is to use '_setof' or '_seqof' or '_choice'
--        or whatever depending on the structure being extracted. 
--
--        Instead of using the default name, we use the
--        following convention. 
--
--              - For SEQUENCE OF and SET OF structures we use SeqOf<Item>s 
--				  or SetOf<Item>s. For example above for SeqOfTokens, 
--				  SeqofCryptTokens and SeqOfOctetStrings.
--
--              - For the various STRING classes we 
--                use the string name. i.e. OctetString.
--			
--				- For SEQUENCE structures use a type name generated from
--				  the field name.
--
--      - For structures that have the same names in multiple
--        protocols. For example, NonStandardParameter is
--        defined in H.225, H.235 and H.245. 
--        We will make these structure names unique by prefixing
--	  	  the protocol name. I.e. H225NonStandardParameter.
--        
--      - All type names in the global namespace will by prefixed
--		  with "Em".
--
--		- The ASN.1 compiler produces a #define for fields in a CHOICE
--		  and OPTIONAL fields in a SEQUENCE. Thus if there are multiple
--		  CHOICEs with identical fields or if there are multiple
--		  SEQUENCES with the same named OPTIONAL field, a naming conflict
--		  arises. To avoid naming conflict, if a structure has a naming
--		  conflict, then every member of the name structure needs to
--		  be named with a unique prefix. For example, Alerting_UUIE
--		  shares an optional h245Address with other UUIE messages. To
--		  avoid a naming conflict, each field in the Alerting_UUIE structure
--		  is prefixed with "alerting".
--
-- ------------------------------------------------------------- --

-- ------------------------------------------------------------- --
-- 
-- Global directives
--
-- ------------------------------------------------------------- --

--<OSS.OBJECTID LONG>--
--<OSS. NOPOINTER>--
--<OSS.
--  UNBOUNDED SEQUENCE OF, SET OF, OBJECT IDENTIFIER>--

--<ASN1.Version 1997 H323-MESSAGES>--

--<ASN1.WorkingSet 
--		H323-MESSAGES-WS 
--			H323-MESSAGES,
--			H235-SECURITY-MESSAGES.ChallengeString,
--			H235-SECURITY-MESSAGES.TimeStamp,
--			H235-SECURITY-MESSAGES.RandomVal,
--			H235-SECURITY-MESSAGES.Password,
--			H235-SECURITY-MESSAGES.EncodedPwdCertToken,
--			H235-SECURITY-MESSAGES.ClearToken,
--			H235-SECURITY-MESSAGES.CryptoToken,
--			H235-SECURITY-MESSAGES.AuthenticationMechanism>--

-- ------------------------------------------------------------- --
--
-- H.235 directives
--
-- ------------------------------------------------------------- --

-- ------------------------------------------------------------- --
-- ChallengeString		::= OCTET STRING (SIZE(8..128))
-- ------------------------------------------------------------- --

--<ASN1.PDU
--		H235-SECURITY-MESSAGES.ChallengeString>--
--<OSS.TYPENAME
--		H235-SECURITY-MESSAGES.ChallengeString 	
--		"EmChallengeString">--

-- ------------------------------------------------------------- --
-- TimeStamp			::= INTEGER(1..4294967295)
-- ------------------------------------------------------------- --

--<ASN1.PDU 
--		H235-SECURITY-MESSAGES.TimeStamp>--
--<OSS.TYPENAME 
--		H235-SECURITY-MESSAGES.TimeStamp 		
--		"EmTimeStamp">--

-- ------------------------------------------------------------- --
-- RandomVal			::= INTEGER
-- ------------------------------------------------------------- --

--<ASN1.PDU 
--		H235-SECURITY-MESSAGES.RandomVal>--
--<OSS.TYPENAME
--		H235-SECURITY-MESSAGES.RandomVal 		
--		"EmRandomVal">--

-- ------------------------------------------------------------- --
-- Password				::= BMPString (SIZE (1..128))
-- ------------------------------------------------------------- --

--<ASN1.PDU 
--		H235-SECURITY-MESSAGES.Password>--
--<OSS.TYPENAME
--		H235-SECURITY-MESSAGES.Password 		
--		"EmPassword">--

-- ------------------------------------------------------------- --
-- Identifier			::= BMPString (SIZE (1..128))
-- ------------------------------------------------------------- --

--<ASN1.PDU
--		H235-SECURITY-MESSAGES.Identifier>--
--<OSS.TYPENAME
--		H235-SECURITY-MESSAGES.Identifier 		
--		"EmIdentifier">--

--------------------------------------------------------------- --
-- ObjectIdentifier 	::= OBJECT IDENTIFIER
-- ------------------------------------------------------------- --

--<OSS.TYPENAME
--		H235-SECURITY-MESSAGES.ObjectIdentifier	
--		"EmObjectIdentifier">--

--------------------------------------------------------------- --
-- OctetString 			::= OCTET STRING
-- ------------------------------------------------------------- --

--<OSS.TYPENAME
--		H235-SECURITY-MESSAGES.OctetString 		
--		"EmOctetString">--

-- ------------------------------------------------------------- --
-- BitString			::= BIT STRING
-- ------------------------------------------------------------- --

--<OSS.TYPENAME
--		H235-SECURITY-MESSAGES.BitString
--		"EmBitString">--

-- ------------------------------------------------------------- --
-- NonStandardParameter ::= SEQUENCE
-- {
-- 	nonStandardIdentifier	OBJECT IDENTIFIER,
-- 	data					OCTET STRING
-- }
-- ------------------------------------------------------------- --

--<ASN1.PDU 
--		H235-SECURITY-MESSAGES.NonStandardParameter>--
--<OSS.TYPENAME
--		H235-SECURITY-MESSAGES.NonStandardParameter 
--		"EmH235NonStandardParameter">--
--<OSS.TYPENAME
--		H235-SECURITY-MESSAGES.NonStandardParameter.nonStandardIdentifier
--		"nonStandardIdentifier">--
--<OSS.TYPENAME
--		H235-SECURITY-MESSAGES.NonStandardParameter.data
--		"data">--

-- ------------------------------------------------------------- --
-- BitString2K ::= BIT STRING (SIZE(0..2048))
--
-- DHset ::= SEQUENCE  
-- {
-- 	halfkey		BIT STRING (SIZE(0..2048)),
-- 	modSize		BIT STRING (SIZE(0..2048)),
-- 	generator	BIT STRING (SIZE(0..2048)),
-- 	...
-- }
-- ------------------------------------------------------------- --

--<ASN1.PDU
--		H235-SECURITY-MESSAGES.BitString2K>--
--<OSS.TYPENAME
--		H235-SECURITY-MESSAGES.BitString2K
--		"EmBitString2K">--

--<ASN1.PDU 
--		H235-SECURITY-MESSAGES.DHset>--
--<OSS.TYPENAME 
--		H235-SECURITY-MESSAGES.DHset 
--		"EmDHset">--
--<OSS.FIELDNAME 
--		H235-SECURITY-MESSAGES.DHset.halfkey
--		"halfkey">--
--<OSS.FIELDNAME 
--		H235-SECURITY-MESSAGES.DHset.modSize
--		"modSize">--
--<OSS.FIELDNAME 
--		H235-SECURITY-MESSAGES.DHset.generator
--		"generator">--
--<OSS.ExtractType
--		H235-SECURITY-MESSAGES.DHset.halfkey>--
--<OSS.TYPENAME
--		H235-SECURITY-MESSAGES.DHset.halfkey
--		"EmBitString2K">--
--<OSS.TYPENAME
--		H235-SECURITY-MESSAGES.DHset.modSize
--		"EmBitString2k">--
--<OSS.TYPENAME
--		H235-SECURITY-MESSAGES.DHset.generator
--		"EmBitString2K">--

-- ------------------------------------------------------------- --
-- TypedCertificate ::= SEQUENCE
-- {
-- 	type			OBJECT IDENTIFIER,
-- 	certificate		OCTET STRING,
-- 	...
-- }
-- ------------------------------------------------------------- --

--<ASN1.PDU 
--		H235-SECURITY-MESSAGES.TypedCertificate>--
--<OSS.TYPENAME 
--		H235-SECURITY-MESSAGES.TypedCertificate 
--		"EmTypedCertificate">--
--<OSS.FIELDNAME 
--		H235-SECURITY-MESSAGES.TypedCertificate.type
--		"type">--
--<OSS.FIELDNAME 
--		H235-SECURITY-MESSAGES.TypedCertificate.certificate
--		"certificate">--
--<OSS.TYPENAME 
--		H235-SECURITY-MESSAGES.TypedCertificate.certificate
--		"EmOctetString">--

-- ------------------------------------------------------------- --
-- AuthenticationMechanism	 ::=CHOICE 
-- {
-- 	dhExch     		NULL, 
-- 	pwdSymEnc		NULL, 
-- 	pwdHash			NULL, 
-- 	certSign		NULL, 
-- 	ipsec			NULL, 
-- 	tls				NULL,
-- 	nonStandard 	NonStandardParameter,
-- 	...
-- }
-- ------------------------------------------------------------- --

--<ASN1.PDU 
--		H235-SECURITY-MESSAGES.AuthenticationMechanism>--
--<OSS.TYPENAME 
--		H235-SECURITY-MESSAGES.AuthenticationMechanism 
--		"EmAuthenticationMechanism">--
--<OSS.FIELDNAME 
--		H235-SECURITY-MESSAGES.AuthenticationMechanism.dhExch
--		"dhExch">--
--<OSS.DefineName 
--		H235-SECURITY-MESSAGES.AuthenticationMechanism.dhExch 
--		"EM_dhExch">--
--<OSS.FIELDNAME 
--		H235-SECURITY-MESSAGES.AuthenticationMechanism.pwdSymEnc
--		"pwdSymEnc">--
--<OSS.DefineName 
--		H235-SECURITY-MESSAGES.AuthenticationMechanism.pwdSymEnc 
--		"EM_pwdSymEnc">--
--<OSS.FIELDNAME 
--		H235-SECURITY-MESSAGES.AuthenticationMechanism.pwdHash
--		"pwdHash">--
--<OSS.DefineName 
--		H235-SECURITY-MESSAGES.AuthenticationMechanism.pwdHash 
--		"EM_pwdHash">--
--<OSS.FIELDNAME 
--		H235-SECURITY-MESSAGES.AuthenticationMechanism.certSign
--		"certSign">--
--<OSS.DefineName 
--		H235-SECURITY-MESSAGES.AuthenticationMechanism.certSign 
--		"EM_certSign">--
--<OSS.FIELDNAME 
--		H235-SECURITY-MESSAGES.AuthenticationMechanism.ipsec
--		"ipsec">--
--<OSS.DefineName 
--		H235-SECURITY-MESSAGES.AuthenticationMechanism.ipsec 
--		"EM_AuthenticationMechanism_ipsec">--
--<OSS.FIELDNAME 
--		H235-SECURITY-MESSAGES.AuthenticationMechanism.tls
--		"tls">--
--<OSS.DefineName 
--		H235-SECURITY-MESSAGES.AuthenticationMechanism.tls 
--		"EM_AuthenticationMechanism_tls">--
--<OSS.FIELDNAME 
--		H235-SECURITY-MESSAGES.AuthenticationMechanism.nonStandard
--		"nonStandard">--
--<OSS.DefineName 
--		H235-SECURITY-MESSAGES.AuthenticationMechanism.nonStandard 
--		"EM_AuthenticationMechanism_nonStandard">--

-- ------------------------------------------------------------- --
-- ClearToken		::= SEQUENCE
-- {	
-- 	tokenOID			OBJECT IDENTIFIER,
-- 	timeStamp			TimeStamp 					OPTIONAL,
-- 	password			Password 					OPTIONAL,
-- 	dhkey				DHset 						OPTIONAL,
-- 	challenge			ChallengeString 			OPTIONAL,
-- 	random				RandomVal 					OPTIONAL,
-- 	certificate			TypedCertificate 			OPTIONAL,
-- 	generalID			Identifier 					OPTIONAL,
-- 	nonStandard 		NonStandardParameter 		OPTIONAL,
-- 	...
-- }
-- ------------------------------------------------------------- --

--<ASN1.PDU 
--		H235-SECURITY-MESSAGES.ClearToken>--
--<OSS.TYPENAME 
--		H235-SECURITY-MESSAGES.ClearToken 
--		"EmClearToken">--
--<OSS.FIELDNAME 
--		H235-SECURITY-MESSAGES.ClearToken.tokenOID
--		"tokenOID">--
--<OSS.FIELDNAME 
--		H235-SECURITY-MESSAGES.ClearToken.timeStamp
--		"timeStamp">--
--<OSS.DefineName 
--		H235-SECURITY-MESSAGES.ClearToken.timeStamp 
--		"EM_timeStamp">--
--<OSS.FIELDNAME 
--		H235-SECURITY-MESSAGES.ClearToken.password
--		"password">--
--<OSS.DefineName 
--		H235-SECURITY-MESSAGES.ClearToken.password 
--		"EM_password">--
--<OSS.FIELDNAME 
--		H235-SECURITY-MESSAGES.ClearToken.dhkey
--		"dhkey">--
--<OSS.DefineName 
--		H235-SECURITY-MESSAGES.ClearToken.dhkey 
--		"EM_dhkey">--
--<OSS.FIELDNAME 
--		H235-SECURITY-MESSAGES.ClearToken.challenge
--		"challenge">--
--<OSS.DefineName 
--		H235-SECURITY-MESSAGES.ClearToken.challenge 
--		"EM_challenge">--
--<OSS.FIELDNAME 
--		H235-SECURITY-MESSAGES.ClearToken.random
--		"random">--
--<OSS.DefineName 
--		H235-SECURITY-MESSAGES.ClearToken.random 
--		"EM_random">--
--<OSS.FIELDNAME 
--		H235-SECURITY-MESSAGES.ClearToken.certificate
--		"certificate">--
--<OSS.DefineName 
--		H235-SECURITY-MESSAGES.ClearToken.certificate 
--		"EM_certificate">--
--<OSS.FIELDNAME 
--		H235-SECURITY-MESSAGES.ClearToken.generalID
--		"generalID">--
--<OSS.DefineName 
--		H235-SECURITY-MESSAGES.ClearToken.generalID 
--		"EM_generalID">--
--<OSS.FIELDNAME 
--		H235-SECURITY-MESSAGES.ClearToken.nonStandard
--		"nonStandard">--
--<OSS.DefineName 
--		H235-SECURITY-MESSAGES.ClearToken.nonStandard 
--		"EM_ClearToken_nonStandard">--

-- ------------------------------------------------------------- --
-- ALGORITHM-IDENTIFIER ::= TYPE-IDENTIFIER
-- 
-- Note: Don't know what this is for.
-- ------------------------------------------------------------- --

-- ------------------------------------------------------------- --
-- Start all the cryptographic parameterized types here....
--
-- 
-- SIGNED { ToBeSigned } ::= SEQUENCE {
--    toBeSigned  	ToBeSigned,
--    algorithmOID  ObjectIdentifier, 
--    paramS 		Params,	// any 'runtime' parameters
--    signature   	BitString
-- } ( CONSTRAINED BY { // Verify or Sign Certificate // } )
-- 
-- 
-- ENCRYPTED { ToBeEncrypted } ::= SEQUENCE {
--    algorithmOID  	ObjectIdentifier, 
--    paramS 			Params,	// any 'runtime' parameters
--    encryptedData  	OctetString
-- } ( CONSTRAINED BY { // Encrypt or Decrypt // ToBeEncrypted } )
-- 
-- HASHED { ToBeHashed } ::= SEQUENCE {
--    algorithmOID  	ObjectIdentifier, 
--    paramS 			Params,	// any 'runtime' parameters
--    hash				BitString
-- } ( CONSTRAINED BY { // Hash // ToBeHashed } )
-- 
-- Note: It is best if we don't apply directives to a
--		 parameterized type. Rather we should apply the 
--		 directives to each instance of the parameterized 
--		 type.
-- ------------------------------------------------------------- --

-- ------------------------------------------------------------- --
-- IV8 ::= OCTET STRING (SIZE(8))
-- ------------------------------------------------------------- --

--<ASN1.PDU
--		H235-SECURITY-MESSAGES.IV8>--
--<OSS.TYPENAME 
--		H235-SECURITY-MESSAGES.IV8 
--		"EmIV8">--

-- ------------------------------------------------------------- --
-- Params ::= SEQUENCE 
-- {
-- 	null		NULL,	
-- 	ranInt		INTEGER 	OPTIONAL, 
-- 	iv8			IV8 		OPTIONAL,	
-- 	...
-- }
-- ------------------------------------------------------------- --

--<ASN1.PDU
--		H235-SECURITY-MESSAGES.Params>--
--<OSS.TYPENAME 
--		H235-SECURITY-MESSAGES.Params 
--		"EmParams">--
--<OSS.FIELDNAME 
--		H235-SECURITY-MESSAGES.Params.null
--		"null">--
--<OSS.FIELDNAME 
--		H235-SECURITY-MESSAGES.Params.ranInt
--		"ranInt">--
--<OSS.DefineName 
--		H235-SECURITY-MESSAGES.Params.ranInt 
--		"EM_ranInt">--
--<OSS.FIELDNAME 
--		H235-SECURITY-MESSAGES.Params.iv8
--		"iv8">--
--<OSS.DefineName 
--		H235-SECURITY-MESSAGES.Params.iv8 
--		"EM_iv8">--

-- ------------------------------------------------------------- --
-- EncodedGeneralToken ::= TYPE-IDENTIFIER.&Type (ClearToken) 
-- PwdCertToken ::= ClearToken (WITH COMPONENTS {..., timeStamp, generalID })
-- EncodedPwdCertToken ::= TYPE-IDENTIFIER.&Type (PwdCertToken)
-- ------------------------------------------------------------- --

--<OSS.TYPENAME 
--		H235-SECURITY-MESSAGES.EncodedGeneralToken 
--		"EmEncodedGeneralToken">--
--<ASN1.PDU
--		H235-SECURITY-MESSAGES.PwdCertToken>--
--<OSS.TYPENAME 
--		H235-SECURITY-MESSAGES.PwdCertToken 
--		"EmPwdCertToken">--
--<OSS.TYPENAME 
--		H235-SECURITY-MESSAGES.EncodedPwdCertToken 
--		"EmEncodedPwdCertToken">--

-- ------------------------------------------------------------- --
-- CryptoPwdEncr ::= ENCRYPTED { EncodedPwdCertToken }
-- ------------------------------------------------------------- --

--<ASN1.PDU
--		H235-SECURITY-MESSAGES.CryptoPwdEncr>--
--<OSS.TYPENAME 
--		H235-SECURITY-MESSAGES.CryptoPwdEncr 
--		"EmCryptoPwdEncr">--
--<OSS.TYPENAME 
--		H235-SECURITY-MESSAGES.CryptoPwdEncr.algorithmOID 
--		"EmObjectIdentifier">--
--<OSS.TYPENAME 
--		H235-SECURITY-MESSAGES.CryptoPwdEncr.paramS 
--		"EmParams">--
--<OSS.TYPENAME 
--		H235-SECURITY-MESSAGES.CryptoPwdEncr.encryptedData 
--		"EmOctetString">--


-- ------------------------------------------------------------- --
-- EncryptedEncodedGeneralToken 	::= ENCRYPTED { EncodedGeneralToken }
-- ------------------------------------------------------------- --

--<ASN1.PDU
--		H235-SECURITY-MESSAGES.EncryptedEncodedGeneralToken>--
--<OSS.TYPENAME 
--		H235-SECURITY-MESSAGES.EncryptedEncodedGeneralToken
--		"EmEncryptedEncodedGeneralToken">--
--<OSS.FIELDNAME 
--		H235-SECURITY-MESSAGES.EncryptedEncodedGeneralToken
--		"token">--
--<OSS.TYPENAME 
--		H235-SECURITY-MESSAGES.EncryptedEncodedGeneralToken.algorithmOID
--		"EmObjectIdentifier">--
--<OSS.FIELDNAME
--		H235-SECURITY-MESSAGES.EncryptedEncodedGeneralToken.algorithmOID
--		"algorithmOID">--
--<OSS.TYPENAME 
--		H235-SECURITY-MESSAGES.EncryptedEncodedGeneralToken.paramS
--		"EmParams">--
--<OSS.FIELDNAME
--		H235-SECURITY-MESSAGES.EncryptedEncodedGeneralToken.paramS
--		"paramS">--
--<OSS.TYPENAME 
--		H235-SECURITY-MESSAGES.EncryptedEncodedGeneralToken.encryptedData
--		"EmOctetString">--
--<OSS.FIELDNAME
--		H235-SECURITY-MESSAGES.EncryptedEncodedGeneralToken.encryptedData
--		"encryptedData">--

-- ------------------------------------------------------------- --
-- SignedEncodedGeneralToken 		::= SIGNED { EncodedGeneralToken }
-- ------------------------------------------------------------- --

--<ASN1.PDU
--		H235-SECURITY-MESSAGES.SignedEncodedGeneralToken>--
--<OSS.TYPENAME 
--		H235-SECURITY-MESSAGES.SignedEncodedGeneralToken
--		"EmSignedEncodedGeneralToken">--
--<OSS.TYPENAME 
--		H235-SECURITY-MESSAGES.SignedEncodedGeneralToken.toBeSigned
--		"EmEncodedGeneralToken">--
--<OSS.FIELDNAME
--		H235-SECURITY-MESSAGES.SignedEncodedGeneralToken.toBeSigned
--		"toBeSigned">--
--<OSS.TYPENAME 
--		H235-SECURITY-MESSAGES.SignedEncodedGeneralToken.algorithmOID
--		"EmObjectIdentifier">--
--<OSS.FIELDNAME
--		H235-SECURITY-MESSAGES.SignedEncodedGeneralToken.algorithmOID
--		"algorithmOID">--
--<OSS.TYPENAME 
--		H235-SECURITY-MESSAGES.SignedEncodedGeneralToken.paramS
--		"EmParams">--
--<OSS.FIELDNAME
--		H235-SECURITY-MESSAGES.SignedEncodedGeneralToken.paramS
--		"paramS">--
--<OSS.TYPENAME 
--		H235-SECURITY-MESSAGES.SignedEncodedGeneralToken.signature
--		"EmBitString">--
--<OSS.FIELDNAME
--		H235-SECURITY-MESSAGES.SignedEncodedGeneralToken.signature
--		"signature">--

-- ------------------------------------------------------------- --
-- HashedEncodedGeneralToken 		::= HASHED { EncodedGeneralToken }
-- ------------------------------------------------------------- --

--<ASN1.PDU
--		H235-SECURITY-MESSAGES.HashedEncodedGeneralToken>--
--<OSS.TYPENAME 
--		H235-SECURITY-MESSAGES.HashedEncodedGeneralToken
--		"EmHashedEncodedGeneralToken">--
--<OSS.TYPENAME 
--		H235-SECURITY-MESSAGES.HashedEncodedGeneralToken.algorithmOID
--		"EmObjectIdentifier">--
--<OSS.FIELDNAME
--		H235-SECURITY-MESSAGES.HashedEncodedGeneralToken.algorithmOID
--		"algorithmOID">--
--<OSS.TYPENAME 
--		H235-SECURITY-MESSAGES.HashedEncodedGeneralToken.paramS
--		"EmParams">--
--<OSS.FIELDNAME
--		H235-SECURITY-MESSAGES.HashedEncodedGeneralToken.paramS
--		"paramS">--
--<OSS.TYPENAME 
--		H235-SECURITY-MESSAGES.HashedEncodedGeneralToken.hash
--		"EmBitString">--
--<OSS.FIELDNAME
--		H235-SECURITY-MESSAGES.HashedEncodedGeneralToken.hash
--		"hash">--

-- ------------------------------------------------------------- --
-- CryptoToken::= CHOICE
-- {
-- 	cryptoEncryptedToken SEQUENCE 
-- 	{
-- 		tokenOID  	ObjectIdentifier, 
-- 		token 		EncryptedEncodedGeneralToken
-- 	},
-- 	cryptoSignedToken  SEQUENCE
-- 	{
-- 		tokenOID  	ObjectIdentifier, 
-- 		token 		SignedEncodedGeneralToken
-- 	},
-- 	cryptoHashedToken SEQUENCE
-- 	{
-- 		tokenOID  		ObjectIdentifier, 
-- 		hashedVals		ClearToken,
-- 		token 			HashedEncodedGeneralToken
-- 	},
-- 	cryptoPwdEncr 	CryptoPwdEncr,
-- 	...
-- }
-- ------------------------------------------------------------- --

--<ASN1.PDU
--		H235-SECURITY-MESSAGES.CryptoToken>--
--<OSS.TYPENAME 
--		H235-SECURITY-MESSAGES.CryptoToken 
--		"EmCryptoToken">--

--<OSS.InlineType 
--		H235-SECURITY-MESSAGES.CryptoToken.cryptoEncryptedToken>--
--<OSS.TYPENAME 
--		H235-SECURITY-MESSAGES.CryptoToken.cryptoEncryptedToken 
--		"EmCryptoEncryptedToken">--
--<OSS.FIELDNAME 
--		H235-SECURITY-MESSAGES.CryptoToken.cryptoEncryptedToken 
--		"cryptoEncryptedToken">--
--<OSS.DefineName
--		H235-SECURITY-MESSAGES.CryptoToken.cryptoEncryptedToken
--		"EM_cryptoEncryptedToken">--
--<OSS.TYPENAME
--		H235-SECURITY-MESSAGES.CryptoToken.cryptoEncryptedToken.tokenOID
--		"EmObjectIdentifier">--
--<OSS.FIELDNAME
--		H235-SECURITY-MESSAGES.CryptoToken.cryptoEncryptedToken.tokenOID
--		"tokenOID">--
--<OSS.FIELDNAME 
--		H235-SECURITY-MESSAGES.CryptoToken.cryptoEncryptedToken.token
--		"token">--

--<OSS.InlineType 
--		H235-SECURITY-MESSAGES.CryptoToken.cryptoSignedToken>--
--<OSS.TYPENAME 
--		H235-SECURITY-MESSAGES.CryptoToken.cryptoSignedToken 
--		"EmCryptoSignedToken">--
--<OSS.FIELDNAME 
--		H235-SECURITY-MESSAGES.CryptoToken.cryptoSignedToken 
--		"cryptoSignedToken">--
--<OSS.DefineName
--		H235-SECURITY-MESSAGES.CryptoToken.cryptoSignedToken
--		"EM_cryptoSignedToken">--
--<OSS.TYPENAME
--		H235-SECURITY-MESSAGES.CryptoToken.cryptoSignedToken.tokenOID
--		"EmObjectIdentifier">--
--<OSS.FIELDNAME
--		H235-SECURITY-MESSAGES.CryptoToken.cryptoSignedToken.tokenOID
--		"tokenOID">--
--<OSS.FIELDNAME 
--		H235-SECURITY-MESSAGES.CryptoToken.cryptoSignedToken.token
--		"token">--

--<OSS.InlineType 
--		H235-SECURITY-MESSAGES.CryptoToken.cryptoHashedToken>--
--<OSS.TYPENAME 
--		H235-SECURITY-MESSAGES.CryptoToken.cryptoHashedToken 
--		"EmCryptoHashedToken">--
--<OSS.FIELDNAME 
--		H235-SECURITY-MESSAGES.CryptoToken.cryptoHashedToken 
--		"cryptoHashedToken">--
--<OSS.DefineName
--		H235-SECURITY-MESSAGES.CryptoToken.cryptoHashedToken
--		"EM_cryptoHashedToken">--
--<OSS.TYPENAME
--		H235-SECURITY-MESSAGES.CryptoToken.cryptoHashedToken.tokenOID
--		"EmObjectIdentifier">--
--<OSS.FIELDNAME
--		H235-SECURITY-MESSAGES.CryptoToken.cryptoHashedToken.tokenOID
--		"tokenOID">--
--<OSS.FIELDNAME 
--		H235-SECURITY-MESSAGES.CryptoToken.cryptoHashedToken.token
--		"token">--

--<OSS.FIELDNAME 
--		H235-SECURITY-MESSAGES.CryptoToken.cryptoPwdEncr 
--		"cryptoPwdEncr">--
--<OSS.DefineName
--		H235-SECURITY-MESSAGES.CryptoToken.cryptoPwdEncr 
--		"EM_cryptoPwdEncr">--

-- -------------------------------------------------------------- --
--
-- H.225 directives
--
-- -------------------------------------------------------------- --

-- -------------------------------------------------------------- --
-- H323-UserInformation ::= SEQUENCE
-- {
--		h323-uu-pdu	H323-UU-PDU,
--		user-data	SEQUENCE
--		{
--			protocol-discriminator		INTEGER	(0..255),
--			user-information			OCTET STRING (SIZE(1..131)),
--			...
--		} OPTIONAL,
--		...
-- }
-- -------------------------------------------------------------- --

--<ASN1.PDU
--		H323-MESSAGES.H323-UserInformation>--
--<OSS.TYPENAME 
--		H323-MESSAGES.H323-UserInformation 
--		"EmH323_UserInformation">--
--<OSS.FIELDNAME	
--		H323-MESSAGES.H323-UserInformation.h323-uu-pdu 
--		"h323_uu_pdu">--
--<OSS.InlineType
--		H323-MESSAGES.H323-UserInformation.user-data>--
--<OSS.TYPENAME
--		H323-MESSAGES.H323-UserInformation.user-data 
--		"EmUserData">--
--<OSS.FIELDNAME	
--		H323-MESSAGES.H323-UserInformation.user-data 
--		"user_data">--
--<OSS.DefineName
--		H323-MESSAGES.H323-UserInformation.user-data 
--		"EM_user_data">--
--<OSS.FIELDNAME	
--		H323-MESSAGES.H323-UserInformation.user-data.protocol-discriminator 
--		"protocol_discriminator">--
--<OSS.TYPENAME
--		H323-MESSAGES.H323-UserInformation.user-data.user-information 
--		"EmUserInformation">--
--<OSS.FIELDNAME	
--		H323-MESSAGES.H323-UserInformation.user-data.user-information 
--		"user_information">--

-- -------------------------------------------------------------- --
-- OctetString					::= OCTET STRING
-- -------------------------------------------------------------- --
--<ASN1.PDU
--		H323-MESSAGES.OctetString>--
--<OSS.TYPENAME
--		H323-MESSAGES.OctetString
--		"EmOctetString">--

-- -------------------------------------------------------------- --
-- ObjectIdentifier				::= OBJECT IDENTIFIER
-- -------------------------------------------------------------- --
--<ASN1.PDU
--		H323-MESSAGES.ObjectIdentifier>--
--<OSS.TYPENAME
--		H323-MESSAGES.ObjectIdentifier
--		"EmObjectIdentifier">--

-- -------------------------------------------------------------- --
-- BitString					::= BIT STRING
-- -------------------------------------------------------------- --
--<ASN1.PDU
--		H323-MESSAGES.BitString>--
--<OSS.TYPENAME
--		H323-MESSAGES.BitString
--		"EmBitString">--

-- -------------------------------------------------------------- --
-- SeqOfOctetString				::= SEQUENCE OF OctetString
-- -------------------------------------------------------------- --
--<ASN1.PDU
--		H323-MESSAGES.SeqOfOctetString>--
--<OSS.TYPENAME 
--		H323-MESSAGES.SeqOfOctetString 			
--		"EmSeqOfOctetString">--
--<OSS.TYPENAME 
--		H323-MESSAGES.SeqOfOctetString.* 		
--		"EmOctetString">--

-- -------------------------------------------------------------- --
-- SeqOfClearToken				::= SEQUENCE OF ClearToken
-- -------------------------------------------------------------- --
--<ASN1.PDU
--		H323-MESSAGES.SeqOfClearToken>--
--<OSS.TYPENAME 
--		H323-MESSAGES.SeqOfClearToken 			
--		"EmSeqOfClearToken">--
--<OSS.TYPENAME 
--		H323-MESSAGES.SeqOfClearToken.* 		
--		"EmClearToken">--

-- -------------------------------------------------------------- --
-- SeqOfCryptoH323Token			::= SEQUENCE OF CryptoH323Token
-- -------------------------------------------------------------- --
--<ASN1.PDU
--		H323-MESSAGES.SeqOfCryptoH323Token>--
--<OSS.TYPENAME 
--		H323-MESSAGES.SeqOfCryptoH323Token 		
--		"EmSeqOfCryptoH323Token">--
--<OSS.TYPENAME 
--		H323-MESSAGES.SeqOfCryptoH323Token.*	
--		"EmCryptoH323Token">--

-- -------------------------------------------------------------- --
-- SeqOfAliasAddress			::= SEQUENCE OF AliasAddress
-- -------------------------------------------------------------- --
--<ASN1.PDU
--		H323-MESSAGES.SeqOfAliasAddress>--
--<OSS.TYPENAME 
--		H323-MESSAGES.SeqOfAliasAddress 		
--		"EmSeqOfAliasAddress">--
--<OSS.TYPENAME 
--		H323-MESSAGES.SeqOfAliasAddress.* 		
--		"EmAliasAddress">--

-- -------------------------------------------------------------- --
-- SeqOfTransportAddress		::= SEQUENCE OF TransportAddress
-- -------------------------------------------------------------- --
--<ASN1.PDU
--		H323-MESSAGES.SeqOfTransportAddress>--
--<OSS.TYPENAME 
--		H323-MESSAGES.SeqOfTransportAddress 	
--		"EmSeqOfH225TransportAddress">--
--<OSS.TYPENAME 
--		H323-MESSAGES.SeqOfTransportAddress.* 	
--		"EmTransportAddress">--

-- -------------------------------------------------------------- --
-- SeqOfCallReferenceValue		::= SEQUENCE OF CallReferenceValue
-- -------------------------------------------------------------- --
--<ASN1.PDU
--		H323-MESSAGES.SeqOfCallReferenceValue>--
--<OSS.TYPENAME 
--		H323-MESSAGES.SeqOfCallReferenceValue 	
--		"EmSeqOfCallReferenceValue">--
--<OSS.TYPENAME 
--		H323-MESSAGES.SeqOfCallReferenceValue.* 
--		"EmCallReferenceValue">--

-- -------------------------------------------------------------- --
-- SeqOfH245Security			::= SEQUENCE OF H245Security
-- -------------------------------------------------------------- --
--<ASN1.PDU
--		H323-MESSAGES.SeqOfH245Security>--
--<OSS.TYPENAME 
--		H323-MESSAGES.SeqOfH245Security 		
--		"EmSeqOfH245Security">--
--<OSS.TYPENAME 
--		H323-MESSAGES.SeqOfH245Security.* 		
--		"EmH245Security">--

-- -------------------------------------------------------------- --
-- SeqOfSupportedProtocols		::= SEQUENCE OF SupportedProtocols
-- -------------------------------------------------------------- --
--<ASN1.PDU
--		H323-MESSAGES.SeqOfSupportedProtocols>--
--<OSS.TYPENAME 
--		H323-MESSAGES.SeqOfSupportedProtocols 	
--		"EmSeqOfSupportedProtocols">--
--<OSS.TYPENAME 
--		H323-MESSAGES.SeqOfSupportedProtocols.* 
--		"EmSupportedProtocols">--

-- -------------------------------------------------------------- --
-- SeqOfConferenceList			::= SEQUENCE OF ConferenceList
-- -------------------------------------------------------------- --
--<ASN1.PDU
--		H323-MESSAGES.SeqOfConferenceList>--
--<OSS.TYPENAME 
--		H323-MESSAGES.SeqOfConferenceList 		
--		"EmSeqOfConferenceList">--
--<OSS.TYPENAME 
--		H323-MESSAGES.SeqOfConferenceList.* 	
--		"EmConferenceList">--

-- -------------------------------------------------------------- --
-- SeqOfDataRate				::= SEQUENCE OF DataRate
-- -------------------------------------------------------------- --
--<ASN1.PDU
--		H323-MESSAGES.SeqOfDataRate>--
--<OSS.TYPENAME 
--		H323-MESSAGES.SeqOfDataRate 			
--		"EmSeqOfDataRate">--
--<OSS.TYPENAME 
--		H323-MESSAGES.SeqOfDataRate.* 			
--		"EmDataRate">--

-- -------------------------------------------------------------- --
-- SeqOfSupportedPrefix			::= SEQUENCE OF SupportedPrefix
-- -------------------------------------------------------------- --
--<ASN1.PDU
--		H323-MESSAGES.SeqOfSupportedPrefix>--
--<OSS.TYPENAME 
--		H323-MESSAGES.SeqOfSupportedPrefix 		
--		"EmSeqOfSupportedPrefix">--
--<OSS.TYPENAME 
--		H323-MESSAGES.SeqOfSupportedPrefix.* 	
--		"EmSupportedPrefix">--

-- -------------------------------------------------------------- --
-- SeqOfAlternateGK				::= SEQUENCE OF AlternateGK
-- -------------------------------------------------------------- --
--<ASN1.PDU
--		H323-MESSAGES.SeqOfAlternateGK>--
--<OSS.TYPENAME 
--		H323-MESSAGES.SeqOfAlternateGK 			
--		"EmSeqOfAlternateGK">--
--<OSS.TYPENAME 
--		H323-MESSAGES.SeqOfAlternateGK.* 		
--		"EmAlternateGK">--

-- -------------------------------------------------------------- --
-- SeqOfEndpoint				::= SEQUENCE OF Endpoint
-- -------------------------------------------------------------- --
--<ASN1.PDU
--		H323-MESSAGES.SeqOfEndpoint>--
--<OSS.TYPENAME 
--		H323-MESSAGES.SeqOfEndpoint 			
--		"EmSeqOfEndpoint">--
--<OSS.TYPENAME 
--		H323-MESSAGES.SeqOfEndpoint.* 			
--		"EmEndpoint">--

-- -------------------------------------------------------------- --
-- SeqOfAuthenticationMechanism	::= SEQUENCE OF AuthenticationMechanism
-- -------------------------------------------------------------- --
--<ASN1.PDU
--		H323-MESSAGES.SeqOfAuthenticationMechanism>--
--<OSS.TYPENAME 
--		H323-MESSAGES.SeqOfAuthenticationMechanism		
--		"EmSeqOfAuthenticationMechanism">--
--<OSS.TYPENAME 
--		H323-MESSAGES.SeqOfAuthenticationMechanism.* 	
--		"EmAuthenticationMechanism">--

-- -------------------------------------------------------------- --
-- SeqOfObjectIdentifier		::= SEQUENCE OF ObjectIdentifier
-- -------------------------------------------------------------- --
--<ASN1.PDU
--		H323-MESSAGES.SeqOfObjectIdentifier>--
--<OSS.TYPENAME 
--		H323-MESSAGES.SeqOfObjectIdentifier 	
--		"EmSeqOfObjectIdentifier">--
--<OSS.TYPENAME 
--		H323-MESSAGES.SeqOfObjectIdentifier.* 	
--		"EmObjectIdentifier">--

-- -------------------------------------------------------------- --
-- SeqOfIntegrityMechanism 		::= SEQUENCE OF IntegrityMechanism
-- -------------------------------------------------------------- --
--<ASN1.PDU
--		H323-MESSAGES.SeqOfIntegrityMechanism>--
--<OSS.TYPENAME 
--		H323-MESSAGES.SeqOfIntegrityMechanism 	
--		"EmSeqOfIntegrityMechanism">--
--<OSS.TYPENAME 
--		H323-MESSAGES.SeqOfIntegrityMechanism.* 
--		"EmIntegrityMechanism">--

-- -------------------------------------------------------------- --
-- SeqOfRTPSession 				::= SEQUENCE OF RTPSession
-- -------------------------------------------------------------- --
--<ASN1.PDU
--		H323-MESSAGES.SeqOfRTPSession>--
--<OSS.TYPENAME 
--		H323-MESSAGES.SeqOfRTPSession 			
--		"EmSeqOfRTPSession">--
--<OSS.TYPENAME 
--		H323-MESSAGES.SeqOfRTPSession.* 		
--		"EmRTPSession">--

-- -------------------------------------------------------------- --
-- SeqOfTransportChannelInfo	::= SEQUENCE OF TransportChannelInfo
-- -------------------------------------------------------------- --
--<ASN1.PDU
--		H323-MESSAGES.SeqOfTransportChannelInfo>--
--<OSS.TYPENAME 
--		H323-MESSAGES.SeqOfTransportChannelInfo 
--		"EmSeqOfTransportChannelInfo">--
--<OSS.TYPENAME 
--		H323-MESSAGES.SeqOfTransportChannelInfo.* 
--		"EmTransportChannelInfo">--

-- -------------------------------------------------------------- --
-- SeqOfConferenceIdentifier	::= SEQUENCE OF ConferenceIdentifier
-- -------------------------------------------------------------- --
--<ASN1.PDU
--		H323-MESSAGES.SeqOfConferenceIdentifier>--
--<OSS.TYPENAME 
--		H323-MESSAGES.SeqOfConferenceIdentifier 
--		"EmSeqOfConferenceIdentifier">--
--<OSS.TYPENAME 
--		H323-MESSAGES.SeqOfConferenceIdentifier.* 
--		"EmConferenceIdentifier">--

-- -------------------------------------------------------------- --
-- SeqOfPerCallInfo				::= SEQUENCE OF PerCallInfo
-- -------------------------------------------------------------- --
--<ASN1.PDU
--		H323-MESSAGES.SeqOfPerCallInfo>--
--<OSS.TYPENAME 
--		H323-MESSAGES.SeqOfPerCallInfo 			
--		"EmSeqOfPerCallInfo">--
--<OSS.TYPENAME 
--		H323-MESSAGES.SeqOfPerCallInfo.* 		
--		"EmPerCallInfo">--

-- -------------------------------------------------------------- --
-- SeqOfPDUInfo					::= SEQUENCE OF PDUInfo
-- -------------------------------------------------------------- --
--<ASN1.PDU
--		H323-MESSAGES.SeqOfPDUInfo>--
--<OSS.TYPENAME 
--		H323-MESSAGES.SeqOfPDUInfo 				
--		"EmSeqOfPDUInfo">--
--<OSS.TYPENAME 
--		H323-MESSAGES.SeqOfPDUInfo.* 			
--		"EmPDUInfo">--

-- -------------------------------------------------------------- --
-- SeqOfNonStandardParameter	::= SEQUENCE OF NonStandardParameter
-- -------------------------------------------------------------- --
--<ASN1.PDU
--		H323-MESSAGES.SeqOfNonStandardParameter>--
--<OSS.TYPENAME 
--		H323-MESSAGES.SeqOfNonStandardParameter 
--		"EmSeqOfNonStandardParameter">--
--<OSS.TYPENAME 
--		H323-MESSAGES.SeqOfNonStandardParameter.* 
--		"EmH225NonStandardParameter">--

-- -------------------------------------------------------------- --
-- H323-UU-PDU ::= SEQUENCE
-- {
-- 	h323-message-body   CHOICE
-- 	{
-- 		setup			Setup-UUIE,
-- 		callProceeding	CallProceeding-UUIE,
-- 		connect			Connect-UUIE,
-- 		alerting		Alerting-UUIE,
-- 		information		Information-UUIE,
-- 		releaseComplete	ReleaseComplete-UUIE,
-- 		facility		Facility-UUIE,
-- 		...,
-- 		progress		Progress-UUIE,
-- 		empty			NULL
-- 	} ,
-- 	
-- 	nonStandardData		NonStandardParameter  OPTIONAL,
-- 	...,
-- 	h4501SupplementaryService	SEQUENCE  OF OCTET STRING OPTIONAL,
-- 	h245Tunneling				BOOLEAN,
-- 	h245Control					SEQUENCE  OF OCTET STRING OPTIONAL,
-- 	nonStandardControl			SEQUENCE  OF NonStandardParameter  OPTIONAL
-- }
-- -------------------------------------------------------------- --

--<ASN1.PDU
--		H323-MESSAGES.H323-UU-PDU>--
--<OSS.TYPENAME 
--		H323-MESSAGES.H323-UU-PDU 
--		"EmH323_UU_PDU">--
--<OSS.ExtractType
--		H323-MESSAGES.H323-UU-PDU.h323-message-body>--
--<OSS.TYPENAME 
--		H323-MESSAGES.H323-UU-PDU.h323-message-body 
--		"EmH323MessageBody">--
--<OSS.FIELDNAME 
--		H323-MESSAGES.H323-UU-PDU.h323-message-body 
--		"h323_message_body">--
--<OSS.FIELDNAME 
--		H323-MESSAGES.H323-UU-PDU.h323-message-body.setup 
--		"setup">--
--<OSS.DefineName
--		H323-MESSAGES.H323-UU-PDU.h323-message-body.setup 
--		"EM_setup">--
--<OSS.FIELDNAME 
--		H323-MESSAGES.H323-UU-PDU.h323-message-body.callProceeding 
--		"callProceeding">--
--<OSS.DefineName
--		H323-MESSAGES.H323-UU-PDU.h323-message-body.callProceeding 
--		"EM_callProceeding">--
--<OSS.FIELDNAME 
--		H323-MESSAGES.H323-UU-PDU.h323-message-body.connect 
--		"connect">--
--<OSS.DefineName
--		H323-MESSAGES.H323-UU-PDU.h323-message-body.connect 
--		"EM_connect">--
--<OSS.FIELDNAME 
--		H323-MESSAGES.H323-UU-PDU.h323-message-body.alerting 
--		"alerting">--
--<OSS.DefineName
--		H323-MESSAGES.H323-UU-PDU.h323-message-body.alerting 
--		"EM_alerting">--
--<OSS.FIELDNAME 
--		H323-MESSAGES.H323-UU-PDU.h323-message-body.information 
--		"information">--
--<OSS.DefineName
--		H323-MESSAGES.H323-UU-PDU.h323-message-body.information 
--		"EM_information">--
--<OSS.FIELDNAME 
--		H323-MESSAGES.H323-UU-PDU.h323-message-body.releaseComplete 
--		"releaseComplete">--
--<OSS.DefineName
--		H323-MESSAGES.H323-UU-PDU.h323-message-body.releaseComplete 
--		"EM_releaseComplete">--
--<OSS.FIELDNAME 
--		H323-MESSAGES.H323-UU-PDU.h323-message-body.facility 
--		"facility">--
--<OSS.DefineName
--		H323-MESSAGES.H323-UU-PDU.h323-message-body.facility 
--		"EM_facility">--
--<OSS.FIELDNAME 
--		H323-MESSAGES.H323-UU-PDU.h323-message-body.progress 
--		"progress">--
--<OSS.DefineName
--		H323-MESSAGES.H323-UU-PDU.h323-message-body.progress 
--		"EM_progress">--
--<OSS.FIELDNAME 
--		H323-MESSAGES.H323-UU-PDU.h323-message-body.empty 
--		"empty">--
--<OSS.DefineName
--		H323-MESSAGES.H323-UU-PDU.h323-message-body.empty 
--		"EM_empty">--
--<OSS.FIELDNAME 
--		H323-MESSAGES.H323-UU-PDU.nonStandardData 
--		"nonStandardData">--
--<OSS.DefineName
--		H323-MESSAGES.H323-UU-PDU.nonStandardData 
--		"EM_H323_UU_PDU_nonStandardData">--
--<OSS.FIELDNAME 
--		H323-MESSAGES.H323-UU-PDU.h4501SupplementaryService 
--		"h4501SupplementaryService">--
--<OSS.DefineName
--		H323-MESSAGES.H323-UU-PDU.h4501SupplementaryService 
--		"EM_h4501SupplementaryService">--
--<OSS.FIELDNAME 
--		H323-MESSAGES.H323-UU-PDU.h245Tunneling 
--		"h245Tunneling">--
--<OSS.DefineName
--		H323-MESSAGES.H323-UU-PDU.h245Tunneling 
--		"EM_h245Tunneling">--
--<OSS.FIELDNAME 
--		H323-MESSAGES.H323-UU-PDU.h245Control 
--		"h245Control">--
--<OSS.DefineName
--		H323-MESSAGES.H323-UU-PDU.h245Control 
--		"EM_h245Control">--
--<OSS.FIELDNAME 
--		H323-MESSAGES.H323-UU-PDU.nonStandardControl 
--		"nonStandardControl">--
--<OSS.DefineName
--		H323-MESSAGES.H323-UU-PDU.nonStandardControl 
--		"EM_nonStandardControl">--

-- ------------------------------------------------------------- --
-- Alerting-UUIE ::= SEQUENCE
-- {
-- 	protocolIdentifier		ProtocolIdentifier,
-- 	destinationInfo			EndpointType,
-- 	h245Address				TransportAddress OPTIONAL,
-- 	...,
-- 	callIdentifier			CallIdentifier,
-- 	h245SecurityMode		H245Security OPTIONAL,
-- 	tokens					SEQUENCE OF ClearToken OPTIONAL,
-- 	cryptoTokens			SEQUENCE OF CryptoH323Token OPTIONAL,
-- 	fastStart				SEQUENCE OF OCTET STRING OPTIONAL
-- }
--
-- ------------------------------------------------------------- --
--<ASN1.PDU
--		H323-MESSAGES.Alerting-UUIE>--
--<OSS.TYPENAME 
--		H323-MESSAGES.Alerting-UUIE
--		"EmAlerting_UUIE">--
--<OSS.FIELDNAME 
--		H323-MESSAGES.Alerting-UUIE.protocolIdentifier 
--		"protocolIdentifier">--
--<OSS.FIELDNAME 
--		H323-MESSAGES.Alerting-UUIE.destinationInfo 
--		"destinationInfo">--
--<OSS.FIELDNAME 
--		H323-MESSAGES.Alerting-UUIE.h245Address 
--		"h245Address">--
--<OSS.DefineName
--		H323-MESSAGES.Alerting-UUIE.h245Address 
--		"EM_Alerting_h245Address">--
--<OSS.FIELDNAME 
--		H323-MESSAGES.Alerting-UUIE.callIdentifier 
--		"callIdentifier">--
--<OSS.DefineName
--		H323-MESSAGES.Alerting-UUIE.callIdentifier 
--		"EM_Alerting_callIdentifier">--
--<OSS.FIELDNAME 
--		H323-MESSAGES.Alerting-UUIE.h245SecurityMode 
--		"h245SecurityMode">--
--<OSS.DefineName
--		H323-MESSAGES.Alerting-UUIE.h245SecurityMode 
--		"EM_Alerting_h245SecurityMode">--
--<OSS.FIELDNAME 
--		H323-MESSAGES.Alerting-UUIE.tokens 
--		"tokens">--
--<OSS.DefineName
--		H323-MESSAGES.Alerting-UUIE.tokens 
--		"EM_Alerting_tokens">--
--<OSS.FIELDNAME 
--		H323-MESSAGES.Alerting-UUIE.cryptoTokens 
--		"cryptoTokens">--
--<OSS.DefineName
--		H323-MESSAGES.Alerting-UUIE.cryptoTokens 
--		"EM_Alerting_cryptoTokens">--
--<OSS.FIELDNAME 
--		H323-MESSAGES.Alerting-UUIE.fastStart 
--		"fastStart">--
--<OSS.DefineName
--		H323-MESSAGES.Alerting-UUIE.fastStart 
--		"EM_Alerting_fastStart">--

-- ------------------------------------------------------------- --
-- CallProceeding-UUIE ::= SEQUENCE
-- {
-- 	protocolIdentifier		ProtocolIdentifier,
-- 	destinationInfo			EndpointType,
-- 	h245Address				TransportAddress OPTIONAL,
-- 	...,
-- 	callIdentifier			CallIdentifier,
-- 	h245SecurityMode		H245Security OPTIONAL,
-- 	tokens					SEQUENCE OF ClearToken OPTIONAL,
-- 	cryptoTokens			SEQUENCE OF CryptoH323Token OPTIONAL,
-- 	fastStart				SEQUENCE OF OCTET STRING OPTIONAL
-- }
-- ------------------------------------------------------------- --

--<ASN1.PDU
--		H323-MESSAGES.CallProceeding-UUIE>--
--<OSS.TYPENAME 
--		H323-MESSAGES.CallProceeding-UUIE 
--		"EmCallProceeding_UUIE">--
--<OSS.FIELDNAME 
--		H323-MESSAGES.CallProceeding-UUIE.protocolIdentifier 
--		"protocolIdentifier">--
--<OSS.FIELDNAME 
--		H323-MESSAGES.CallProceeding-UUIE.destinationInfo 
--		"destinationInfo">--
--<OSS.FIELDNAME 
--		H323-MESSAGES.CallProceeding-UUIE.h245Address 
--		"h245Address">--
--<OSS.DefineName
--		H323-MESSAGES.CallProceeding-UUIE.h245Address 
--		"EM_CallProceeding_h245Address">--
--<OSS.FIELDNAME 
--		H323-MESSAGES.CallProceeding-UUIE.callIdentifier 
--		"callIdentifier">--
--<OSS.DefineName
--		H323-MESSAGES.CallProceeding-UUIE.callIdentifier 
--		"EM_CallProceeding_callIdentifier">--
--<OSS.FIELDNAME 
--		H323-MESSAGES.CallProceeding-UUIE.h245SecurityMode 
--		"h245SecurityMode">--
--<OSS.DefineName
--		H323-MESSAGES.CallProceeding-UUIE.h245SecurityMode 
--		"EM_CallProceeding_h245SecurityMode">--
--<OSS.FIELDNAME 
--		H323-MESSAGES.CallProceeding-UUIE.tokens 
--		"tokens">--
--<OSS.DefineName
--		H323-MESSAGES.CallProceeding-UUIE.tokens 
--		"EM_CallProceeding_tokens">--
--<OSS.FIELDNAME 
--		H323-MESSAGES.CallProceeding-UUIE.cryptoTokens 
--		"cryptoTokens">--
--<OSS.DefineName
--		H323-MESSAGES.CallProceeding-UUIE.cryptoTokens 
--		"EM_CallProceeding_cryptoTokens">--
--<OSS.FIELDNAME 
--		H323-MESSAGES.CallProceeding-UUIE.fastStart 
--		"fastStart">--
--<OSS.DefineName
--		H323-MESSAGES.CallProceeding-UUIE.fastStart 
--		"EM_CallProceeding_fastStart">--

-- ------------------------------------------------------------- --
-- Connect-UUIE ::= SEQUENCE
-- {
-- 	protocolIdentifier	ProtocolIdentifier,
-- 	h245Address			TransportAddress OPTIONAL,
-- 	destinationInfo		EndpointType,
-- 	conferenceID		ConferenceIdentifier,
-- 	...,
-- 	callIdentifier		CallIdentifier,
-- 	h245SecurityMode	H245Security OPTIONAL,
-- 	tokens				SEQUENCE OF ClearToken OPTIONAL,
-- 	cryptoTokens		SEQUENCE OF CryptoH323Token OPTIONAL,
-- 	fastStart			SEQUENCE OF OCTET STRING OPTIONAL
-- }
-- ------------------------------------------------------------- --

--<ASN1.PDU
--		H323-MESSAGES.Connect-UUIE>--
--<OSS.TYPENAME 
--		H323-MESSAGES.Connect-UUIE
--		"EmConnect_UUIE">--
--<OSS.FIELDNAME 
--		H323-MESSAGES.Connect-UUIE.protocolIdentifier
--		"protocolIdentifier">--
--<OSS.FIELDNAME 
--		H323-MESSAGES.Connect-UUIE.h245Address
--		"h245Address">--
--<OSS.DefineName
--		H323-MESSAGES.Connect-UUIE.h245Address
--		"EM_Connect_h245Address">--
--<OSS.FIELDNAME 
--		H323-MESSAGES.Connect-UUIE.destinationInfo
--		"destinationInfo">--
--<OSS.FIELDNAME 
--		H323-MESSAGES.Connect-UUIE.conferenceID
--		"conferenceID">--
--<OSS.FIELDNAME 
--		H323-MESSAGES.Connect-UUIE.callIdentifier
--		"callIdentifier">--
--<OSS.DefineName
--		H323-MESSAGES.Connect-UUIE.callIdentifier
--		"EM_Connect_callIdentifier">--
--<OSS.FIELDNAME 
--		H323-MESSAGES.Connect-UUIE.h245SecurityMode
--		"h245SecurityMode">--
--<OSS.DefineName
--		H323-MESSAGES.Connect-UUIE.h245SecurityMode
--		"EM_Connect_h245SecurityMode">--
--<OSS.FIELDNAME 
--		H323-MESSAGES.Connect-UUIE.tokens
--		"tokens">--
--<OSS.DefineName
--		H323-MESSAGES.Connect-UUIE.tokens
--		"EM_Connect_tokens">--
--<OSS.FIELDNAME 
--		H323-MESSAGES.Connect-UUIE.cryptoTokens
--		"cryptoTokens">--
--<OSS.DefineName
--		H323-MESSAGES.Connect-UUIE.cryptoTokens
--		"EM_Connect_cryptoTokens">--
--<OSS.FIELDNAME 
--		H323-MESSAGES.Connect-UUIE.fastStart
--		"fastStart">--
--<OSS.DefineName
--		H323-MESSAGES.Connect-UUIE.fastStart
--		"EM_Connect_fastStart">--

-- ------------------------------------------------------------- --
-- Information-UUIE	::= SEQUENCE
-- {
-- 	protocolIdentifier	ProtocolIdentifier,
-- 	...,
-- 	callIdentifier		CallIdentifier
-- }
-- ------------------------------------------------------------- --

--<ASN1.PDU
--		H323-MESSAGES.Information-UUIE>--
--<OSS.TYPENAME 
--		H323-MESSAGES.Information-UUIE
--		"EmInformation_UUIE">--
--<OSS.FIELDNAME 
--		H323-MESSAGES.Information-UUIE.protocolIdentifier
--		"protocolIdentifier">--
--<OSS.FIELDNAME 
--		H323-MESSAGES.Information-UUIE.callIdentifier
--		"callIdentifier">--
--<OSS.DefineName
--		H323-MESSAGES.Information-UUIE.callIdentifier
--		"EM_Information_callIdentifier">--

-- ------------------------------------------------------------- --
-- ReleaseComplete-UUIE ::= SEQUENCE
-- {
-- 	protocolIdentifier	ProtocolIdentifier,
-- 	reason				ReleaseCompleteReason OPTIONAL,
-- 	...,
-- 	callIdentifier		CallIdentifier
-- }
-- ------------------------------------------------------------- --

--<ASN1.PDU
--		H323-MESSAGES.ReleaseComplete-UUIE>--
--<OSS.TYPENAME 
--		H323-MESSAGES.ReleaseComplete-UUIE
--		"EmReleaseComplete_UUIE">--
--<OSS.FIELDNAME 
--		H323-MESSAGES.ReleaseComplete-UUIE.protocolIdentifier
--		"protocolIdentifier">--
--<OSS.FIELDNAME 
--		H323-MESSAGES.ReleaseComplete-UUIE.reason
--		"reason">--
--<OSS.DefineName
--		H323-MESSAGES.ReleaseComplete-UUIE.reason
--		"EM_ReleaseComplete_reason">--
--<OSS.FIELDNAME 
--		H323-MESSAGES.ReleaseComplete-UUIE.callIdentifier
--		"callIdentifier">--
--<OSS.DefineName
--		H323-MESSAGES.ReleaseComplete-UUIE.callIdentifier
--		"EM_ReleaseComplete_callIdentifier">--

-- ------------------------------------------------------------- --
-- ReleaseCompleteReason ::= CHOICE
-- {
-- 	noBandwidth					NULL,
-- 	gatekeeperResources			NULL,
-- 	unreachableDestination		NULL,
-- 	destinationRejection		NULL,
-- 	invalidRevision				NULL,
-- 	noPermission				NULL,
-- 	unreachableGatekeeper		NULL,
-- 	gatewayResources			NULL,
-- 	badFormatAddress			NULL,
-- 	adaptiveBusy				NULL,
-- 	inConf						NULL,
-- 	undefinedReason				NULL,
-- 	...,
-- 	facilityCallDeflection		NULL,
-- 	securityDenied				NULL,
-- 	calledPartyNotRegistered	NULL,
-- 	callerNotRegistered			NULL	
-- }
-- ------------------------------------------------------------- --

--<ASN1.PDU
--		H323-MESSAGES.ReleaseCompleteReason>--
--<OSS.TYPENAME 
--		H323-MESSAGES.ReleaseCompleteReason
--		"EmReleaseCompleteReason">--
--<OSS.FIELDNAME 
--		H323-MESSAGES.ReleaseCompleteReason.noBandwidth
--		"noBandwidth">--
--<OSS.DefineName
--		H323-MESSAGES.ReleaseCompleteReason.noBandwidth
--		"EM_noBandwidth">--
--<OSS.FIELDNAME 
--		H323-MESSAGES.ReleaseCompleteReason.gatekeeperResources
--		"gatekeeperResources">--
--<OSS.DefineName
--		H323-MESSAGES.ReleaseCompleteReason.gatekeeperResources
--		"EM_gatekeeperResources">--
--<OSS.FIELDNAME 
--		H323-MESSAGES.ReleaseCompleteReason.unreachableDestination
--		"unreachableDestination">--
--<OSS.DefineName
--		H323-MESSAGES.ReleaseCompleteReason.unreachableDestination
--		"EM_unreachableDestination">--
--<OSS.FIELDNAME 
--		H323-MESSAGES.ReleaseCompleteReason.destinationRejection
--		"destinationRejection">--
--<OSS.DefineName
--		H323-MESSAGES.ReleaseCompleteReason.destinationRejection
--		"EM_destinationRejection">--
--<OSS.FIELDNAME 
--		H323-MESSAGES.ReleaseCompleteReason.invalidRevision
--		"invalidRevision">--
--<OSS.DefineName
--		H323-MESSAGES.ReleaseCompleteReason.invalidRevision
--		"EM_ReleaseComplete_invalidRevision">--
--<OSS.FIELDNAME 
--		H323-MESSAGES.ReleaseCompleteReason.noPermission
--		"noPermission">--
--<OSS.DefineName
--		H323-MESSAGES.ReleaseCompleteReason.noPermission
--		"EM_noPermission">--
--<OSS.FIELDNAME 
--		H323-MESSAGES.ReleaseCompleteReason.unreachableGatekeeper
--		"unreachableGatekeeper">--
--<OSS.DefineName
--		H323-MESSAGES.ReleaseCompleteReason.unreachableGatekeeper
--		"EM_unreachableGatekeeper">--
--<OSS.FIELDNAME 
--		H323-MESSAGES.ReleaseCompleteReason.gatewayResources
--		"gatewayResources">--
--<OSS.DefineName
--		H323-MESSAGES.ReleaseCompleteReason.gatewayResources
--		"EM_gatewayResources">--
--<OSS.FIELDNAME 
--		H323-MESSAGES.ReleaseCompleteReason.badFormatAddress
--		"badFormatAddress">--
--<OSS.DefineName
--		H323-MESSAGES.ReleaseCompleteReason.badFormatAddress
--		"EM_badFormatAddress">--
--<OSS.FIELDNAME 
--		H323-MESSAGES.ReleaseCompleteReason.adaptiveBusy
--		"adaptiveBusy">--
--<OSS.DefineName
--		H323-MESSAGES.ReleaseCompleteReason.adaptiveBusy
--		"EM_adaptiveBusy">--
--<OSS.FIELDNAME 
--		H323-MESSAGES.ReleaseCompleteReason.inConf
--		"inConf">--
--<OSS.DefineName
--		H323-MESSAGES.ReleaseCompleteReason.inConf
--		"EM_inConf">--
--<OSS.FIELDNAME 
--		H323-MESSAGES.ReleaseCompleteReason.undefinedReason
--		"undefinedReason">--
--<OSS.DefineName
--		H323-MESSAGES.ReleaseCompleteReason.undefinedReason
--		"EM_ReleaseComplete_undefinedReason">--
--<OSS.FIELDNAME 
--		H323-MESSAGES.ReleaseCompleteReason.facilityCallDeflection
--		"facilityCallDeflection">--
--<OSS.DefineName
--		H323-MESSAGES.ReleaseCompleteReason.facilityCallDeflection
--		"EM_facilityCallDeflection">--
--<OSS.FIELDNAME 
--		H323-MESSAGES.ReleaseCompleteReason.securityDenied
--		"securityDenied">--
--<OSS.DefineName
--		H323-MESSAGES.ReleaseCompleteReason.securityDenied
--		"EM_securityDenied">--
--<OSS.FIELDNAME 
--		H323-MESSAGES.ReleaseCompleteReason.calledPartyNotRegistered
--		"calledPartyNotRegistered">--
--<OSS.DefineName
--		H323-MESSAGES.ReleaseCompleteReason.calledPartyNotRegistered
--		"EM_ReleaseComplete_calledPartyNotRegistered">--
--<OSS.FIELDNAME 
--		H323-MESSAGES.ReleaseCompleteReason.callerNotRegistered
--		"callerNotRegistered">--
--<OSS.DefineName
--		H323-MESSAGES.ReleaseCompleteReason.callerNotRegistered
--		"EM_ReleaseComplete_callerNotRegistered">--

-- ------------------------------------------------------------- --
-- Setup-UUIE ::= SEQUENCE
-- {
-- 	protocolIdentifier		ProtocolIdentifier,
-- 	h245Address				TransportAddress OPTIONAL,
-- 	sourceAddress			SEQUENCE OF AliasAddress OPTIONAL,
-- 	sourceInfo				EndpointType,
-- 	destinationAddress		SEQUENCE OF AliasAddress OPTIONAL,
-- 	destCallSignalAddress	TransportAddress OPTIONAL,
-- 	destExtraCallInfo		SEQUENCE OF AliasAddress OPTIONAL,
-- 	destExtraCRV			SEQUENCE OF CallReferenceValue OPTIONAL,
-- 	activeMC				BOOLEAN,
-- 	conferenceID			ConferenceIdentifier,
-- 	conferenceGoal			CHOICE
-- 	{
-- 		create		NULL,
-- 		join		NULL,
-- 		invite		NULL,
-- 		...,
-- 		capability-negotiation				NULL,
-- 		callIndependentSupplementaryService	NULL
-- 	},
-- 	callServices			QseriesOptions OPTIONAL,
-- 	callType				CallType,
-- 	...,
-- 	sourceCallSignalAddress	TransportAddress OPTIONAL,
-- 	remoteExtensionAddress	AliasAddress OPTIONAL,
-- 	callIdentifier			CallIdentifier,
-- 	h245SecurityCapability	SEQUENCE OF H245Security OPTIONAL,
-- 	tokens					SEQUENCE OF ClearToken OPTIONAL,
-- 	cryptoTokens			SEQUENCE OF CryptoH323Token OPTIONAL,
-- 	fastStart				SEQUENCE OF OCTET STRING OPTIONAL,
-- 	mediaWaitForConnect		BOOLEAN,
-- 	canOverlapSend			BOOLEAN
-- }
-- ------------------------------------------------------------- --

--<ASN1.PDU
--		H323-MESSAGES.Setup-UUIE>--
--<OSS.TYPENAME 
--		H323-MESSAGES.Setup-UUIE
--		"EmSetup_UUIE">--
--<OSS.FIELDNAME 
--		H323-MESSAGES.Setup-UUIE.protocolIdentifier
--		"protocolIdentifier">--
--<OSS.FIELDNAME 
--		H323-MESSAGES.Setup-UUIE.h245Address
--		"h245Address">--
--<OSS.DefineName
--		H323-MESSAGES.Setup-UUIE.h245Address
--		"EM_Setup_h245Address">--
--<OSS.FIELDNAME 
--		H323-MESSAGES.Setup-UUIE.sourceAddress
--		"sourceAddress">--
--<OSS.DefineName
--		H323-MESSAGES.Setup-UUIE.sourceAddress
--		"EM_sourceAddress">--
--<OSS.FIELDNAME 
--		H323-MESSAGES.Setup-UUIE.sourceInfo
--		"sourceInfo">--
--<OSS.FIELDNAME 
--		H323-MESSAGES.Setup-UUIE.destinationAddress
--		"destinationAddress">--
--<OSS.DefineName
--		H323-MESSAGES.Setup-UUIE.destinationAddress
--		"EM_destinationAddress">--
--<OSS.FIELDNAME 
--		H323-MESSAGES.Setup-UUIE.destCallSignalAddress
--		"destCallSignalAddress">--
--<OSS.DefineName
--		H323-MESSAGES.Setup-UUIE.destCallSignalAddress
--		"EM_Setup_destCallSignalAddress">--
--<OSS.FIELDNAME 
--		H323-MESSAGES.Setup-UUIE.destExtraCallInfo
--		"destExtraCallInfo">--
--<OSS.DefineName
--		H323-MESSAGES.Setup-UUIE.destExtraCallInfo
--		"EM_Setup_destExtraCallInfo">--
--<OSS.FIELDNAME 
--		H323-MESSAGES.Setup-UUIE.destExtraCRV
--		"destExtraCRV">--
--<OSS.DefineName
--		H323-MESSAGES.Setup-UUIE.destExtraCRV
--		"EM_destExtraCRV">--
--<OSS.FIELDNAME 
--		H323-MESSAGES.Setup-UUIE.activeMC
--		"activeMC">--
--<OSS.FIELDNAME 
--		H323-MESSAGES.Setup-UUIE.conferenceID
--		"conferenceID">--
--<OSS.TYPENAME 
--		H323-MESSAGES.Setup-UUIE.conferenceGoal
--		"EmConferenceGoal">--
--<OSS.FIELDNAME 
--		H323-MESSAGES.Setup-UUIE.conferenceGoal
--		"conferenceGoal">--
--<OSS.FIELDNAME 
--		H323-MESSAGES.Setup-UUIE.conferenceGoal.create
--		"create">--
--<OSS.DefineName
--		H323-MESSAGES.Setup-UUIE.conferenceGoal.create
--		"EM_create">--
--<OSS.FIELDNAME 
--		H323-MESSAGES.Setup-UUIE.conferenceGoal.join
--		"join">--
--<OSS.DefineName
--		H323-MESSAGES.Setup-UUIE.conferenceGoal.join
--		"EM_join">--
--<OSS.FIELDNAME 
--		H323-MESSAGES.Setup-UUIE.conferenceGoal.invite
--		"invite">--
--<OSS.DefineName
--		H323-MESSAGES.Setup-UUIE.conferenceGoal.invite
--		"EM_invite">--
--<OSS.FIELDNAME 
--		H323-MESSAGES.Setup-UUIE.conferenceGoal.capability-negotiation
--		"capability_negotiation">--
--<OSS.DefineName
--		H323-MESSAGES.Setup-UUIE.conferenceGoal.capability-negotiation
--		"EM_capability_negotiation">--
--<OSS.FIELDNAME 
--		H323-MESSAGES.Setup-UUIE.conferenceGoal.callIndependentSupplementaryService
--		"callIndSuppService">--
--<OSS.DefineName
--		H323-MESSAGES.Setup-UUIE.conferenceGoal.callIndependentSupplementaryService
--		"EM_callIndSuppService">--
--<OSS.FIELDNAME 
--		H323-MESSAGES.Setup-UUIE.callServices
--		"callServices">--
--<OSS.DefineName
--		H323-MESSAGES.Setup-UUIE.callServices
--		"EM_Setup_callServices">--
--<OSS.FIELDNAME 
--		H323-MESSAGES.Setup-UUIE.callType
--		"callType">--
--<OSS.FIELDNAME 
--		H323-MESSAGES.Setup-UUIE.sourceCallSignalAddress
--		"sourceCallSignalAddress">--
--<OSS.DefineName
--		H323-MESSAGES.Setup-UUIE.sourceCallSignalAddress
--		"EM_sourceCallSignalAddress">--
--<OSS.FIELDNAME 
--		H323-MESSAGES.Setup-UUIE.remoteExtensionAddress
--		"remoteExtensionAddress">--
--<OSS.DefineName
--		H323-MESSAGES.Setup-UUIE.remoteExtensionAddress
--		"EM_Setup_remoteExtensionAddress">--
--<OSS.FIELDNAME 
--		H323-MESSAGES.Setup-UUIE.callIdentifier
--		"callIdentifier">--
--<OSS.DefineName
--		H323-MESSAGES.Setup-UUIE.callIdentifier
--		"EM_Setup_callIdentifier">--
--<OSS.FIELDNAME 
--		H323-MESSAGES.Setup-UUIE.h245SecurityCapability
--		"h245SecurityCapability">--
--<OSS.DefineName
--		H323-MESSAGES.Setup-UUIE.h245SecurityCapability
--		"EM_h245SecurityCapability">--
--<OSS.FIELDNAME 
--		H323-MESSAGES.Setup-UUIE.tokens
--		"tokens">--
--<OSS.DefineName
--		H323-MESSAGES.Setup-UUIE.tokens
--		"EM_Setup_tokens">--
--<OSS.FIELDNAME 
--		H323-MESSAGES.Setup-UUIE.cryptoTokens
--		"cryptoTokens">--
--<OSS.DefineName
--		H323-MESSAGES.Setup-UUIE.cryptoTokens
--		"EM_Setup_cryptoTokens">--
--<OSS.FIELDNAME 
--		H323-MESSAGES.Setup-UUIE.fastStart
--		"fastStart">--
--<OSS.DefineName
--		H323-MESSAGES.Setup-UUIE.fastStart
--		"EM_Setup_fastStart">--
--<OSS.FIELDNAME 
--		H323-MESSAGES.Setup-UUIE.mediaWaitForConnect
--		"mediaWaitForConnect">--
--<OSS.DefineName
--		H323-MESSAGES.Setup-UUIE.mediaWaitForConnect
--		"EM_mediaWaitForConnect">--
--<OSS.FIELDNAME 
--		H323-MESSAGES.Setup-UUIE.canOverlapSend
--		"canOverlapSend">--
--<OSS.DefineName
--		H323-MESSAGES.Setup-UUIE.canOverlapSend
--		"EM_canOverlapSend">--

-- ------------------------------------------------------------- --
-- Facility-UUIE ::= SEQUENCE
-- {
-- 	protocolIdentifier		ProtocolIdentifier,
-- 	alternativeAddress		TransportAddress OPTIONAL,
-- 	alternativeAliasAddress	SEQUENCE OF AliasAddress OPTIONAL,
-- 	conferenceID			ConferenceIdentifier OPTIONAL,
-- 	reason					FacilityReason,
-- 	...,
-- 	callIdentifier			CallIdentifier,
-- 	destExtraCallInfo		SEQUENCE OF AliasAddress OPTIONAL,
-- 	remoteExtensionAddress	AliasAddress OPTIONAL,
-- 	tokens					SEQUENCE OF ClearToken OPTIONAL,
-- 	cryptoTokens			SEQUENCE OF CryptoH323Token OPTIONAL,
-- 	conferences				SEQUENCE OF ConferenceList OPTIONAL,
-- 	h245Address				TransportAddress OPTIONAL,
--	fastStart				SeqOfOctetString OPTIONAL
-- }
-- ------------------------------------------------------------- --

--<ASN1.PDU
--		H323-MESSAGES.Facility-UUIE>--
--<OSS.TYPENAME 
--		H323-MESSAGES.Facility-UUIE 
--		"EmFacility_UUIE">--
--<OSS.FIELDNAME 
--		H323-MESSAGES.Facility-UUIE.protocolIdentifier
--		"protocolIdentifier">--
--<OSS.FIELDNAME 
--		H323-MESSAGES.Facility-UUIE.alternativeAddress
--		"altAddress">--
--<OSS.DefineName
--		H323-MESSAGES.Facility-UUIE.alternativeAddress
--		"EM_altAddress">--
--<OSS.FIELDNAME 
--		H323-MESSAGES.Facility-UUIE.alternativeAliasAddress
--		"altAliasAddress">--
--<OSS.DefineName
--		H323-MESSAGES.Facility-UUIE.alternativeAliasAddress
--		"EM_altAliasAddress">--
--<OSS.FIELDNAME 
--		H323-MESSAGES.Facility-UUIE.conferenceID
--		"conferenceID">--
--<OSS.DefineName
--		H323-MESSAGES.Facility-UUIE.conferenceID
--		"EM_Facility_conferenceID">--
--<OSS.FIELDNAME 
--		H323-MESSAGES.Facility-UUIE.reason
--		"reason">--
--<OSS.FIELDNAME 
--		H323-MESSAGES.Facility-UUIE.callIdentifier
--		"callIdentifier">--
--<OSS.DefineName
--		H323-MESSAGES.Facility-UUIE.callIdentifier
--		"EM_Facility_callIdentifier">--
--<OSS.FIELDNAME 
--		H323-MESSAGES.Facility-UUIE.destExtraCallInfo
--		"destExtraCallInfo">--
--<OSS.DefineName
--		H323-MESSAGES.Facility-UUIE.destExtraCallInfo
--		"EM_Facility_destExtraCallInfo">--
--<OSS.FIELDNAME 
--		H323-MESSAGES.Facility-UUIE.remoteExtensionAddress
--		"remoteExtensionAddress">--
--<OSS.DefineName
--		H323-MESSAGES.Facility-UUIE.remoteExtensionAddress
--		"EM_Facility_remoteExtensionAddress">--
--<OSS.FIELDNAME 
--		H323-MESSAGES.Facility-UUIE.tokens
--		"tokens">--
--<OSS.DefineName
--		H323-MESSAGES.Facility-UUIE.tokens
--		"EM_Facility_tokens">--
--<OSS.FIELDNAME 
--		H323-MESSAGES.Facility-UUIE.cryptoTokens
--		"cryptoTokens">--
--<OSS.DefineName
--		H323-MESSAGES.Facility-UUIE.cryptoTokens
--		"EM_Facility_cryptoTokens">--
--<OSS.FIELDNAME 
--		H323-MESSAGES.Facility-UUIE.conferences
--		"conferences">--
--<OSS.DefineName
--		H323-MESSAGES.Facility-UUIE.conferences
--		"EM_conferences">--
--<OSS.FIELDNAME 
--		H323-MESSAGES.Facility-UUIE.h245Address
--		"h245Address">--
--<OSS.DefineName
--		H323-MESSAGES.Facility-UUIE.h245Address
--		"EM_Facility_h245Address">--
--<OSS.FIELDNAME 
--		H323-MESSAGES.Facility-UUIE.fastStart
--		"fastStart">--
--<OSS.DefineName
--		H323-MESSAGES.Facility-UUIE.fastStart
--		"EM_Facility_fastStart">--

-- ------------------------------------------------------------- --
-- ConferenceList ::= SEQUENCE
-- {
-- 	conferenceID		ConferenceIdentifier OPTIONAL,
-- 	conferenceAlias		AliasAddress OPTIONAL,
-- 	nonStandardData		NonStandardParameter OPTIONAL,
-- 	...
-- }
-- ------------------------------------------------------------- --

--<ASN1.PDU
--		H323-MESSAGES.ConferenceList>--
--<OSS.TYPENAME 
--		H323-MESSAGES.ConferenceList 
--		"EmConferenceList">--
--<OSS.FIELDNAME 
--		H323-MESSAGES.ConferenceList.conferenceID
--		"conferenceID">--
--<OSS.DefineName
--		H323-MESSAGES.ConferenceList.conferenceID
--		"EM_ConferenceList_conferenceID">--
--<OSS.FIELDNAME 
--		H323-MESSAGES.ConferenceList.conferenceAlias
--		"conferenceAlias">--
--<OSS.DefineName
--		H323-MESSAGES.ConferenceList.conferenceAlias
--		"EM_conferenceAlias">--
--<OSS.FIELDNAME 
--		H323-MESSAGES.ConferenceList.nonStandardData
--		"nonStandardData">--
--<OSS.DefineName
--		H323-MESSAGES.ConferenceList.nonStandardData
--		"EM_ConferenceList_nonStandardData">--

-- ------------------------------------------------------------- --
-- FacilityReason ::= CHOICE
-- {
-- 	routeCallToGatekeeper	NULL,
-- 	callForwarded			NULL,
-- 	routeCallToMC			NULL,
-- 	undefinedReason			NULL,
-- 	...,
-- 	conferenceListChoice	NULL,
-- 	startH245				NULL
-- }
--
-- ------------------------------------------------------------- --

--<ASN1.PDU
--		H323-MESSAGES.FacilityReason>--
--<OSS.TYPENAME 
--		H323-MESSAGES.FacilityReason 
--		"EmFacilityReason">--
--<OSS.FIELDNAME 
--		H323-MESSAGES.FacilityReason.routeCallToGatekeeper
--		"routeCallToGatekeeper">--
--<OSS.DefineName
--		H323-MESSAGES.FacilityReason.routeCallToGatekeeper
--		"EM_Facility_routeCallToGatekeeper">--
--<OSS.FIELDNAME 
--		H323-MESSAGES.FacilityReason.callForwarded
--		"callForwarded">--
--<OSS.DefineName
--		H323-MESSAGES.FacilityReason.callForwarded
--		"EM_callForwarded">--
--<OSS.FIELDNAME 
--		H323-MESSAGES.FacilityReason.routeCallToMC
--		"routeCallToMC">--
--<OSS.DefineName
--		H323-MESSAGES.FacilityReason.routeCallToMC
--		"EM_routeCallToMC">--
--<OSS.FIELDNAME 
--		H323-MESSAGES.FacilityReason.undefinedReason
--		"undefinedReason">--
--<OSS.DefineName
--		H323-MESSAGES.FacilityReason.undefinedReason
--		"EM_Facility_undefinedReason">--
--<OSS.FIELDNAME 
--		H323-MESSAGES.FacilityReason.conferenceListChoice
--		"conferenceListChoice">--
--<OSS.DefineName
--		H323-MESSAGES.FacilityReason.conferenceListChoice
--		"EM_conferenceListChoice">--
--<OSS.FIELDNAME 
--		H323-MESSAGES.FacilityReason.startH245
--		"startH245">--
--<OSS.DefineName
--		H323-MESSAGES.FacilityReason.startH245
--		"EM_startH245">--

-- ------------------------------------------------------------- --
-- Progress-UUIE ::= SEQUENCE
-- {
-- 	protocolIdentifier	ProtocolIdentifier,
-- 	destinationInfo		EndpointType,
-- 	h245Address			TransportAddress OPTIONAL,
-- 	callIdentifier		CallIdentifier,
-- 	h245SecurityMode	H245Security OPTIONAL,
-- 	tokens				SEQUENCE OF ClearToken OPTIONAL,
-- 	cryptoTokens		SEQUENCE OF CryptoH323Token OPTIONAL,
-- 	fastStart			SEQUENCE OF OCTET STRING OPTIONAL,
-- 	...
-- }
-- ------------------------------------------------------------- --

--<ASN1.PDU
--		H323-MESSAGES.Progress-UUIE>--
--<OSS.TYPENAME 
--		H323-MESSAGES.Progress-UUIE
--		"EmProgress_UUIE">--
--<OSS.FIELDNAME 
--		H323-MESSAGES.Progress-UUIE.protocolIdentifier
--		"protocolIdentifier">--
--<OSS.FIELDNAME 
--		H323-MESSAGES.Progress-UUIE.destinationInfo
--		"destinationInfo">--
--<OSS.FIELDNAME 
--		H323-MESSAGES.Progress-UUIE.h245Address
--		"h245Address">--
--<OSS.DefineName
--		H323-MESSAGES.Progress-UUIE.h245Address
--		"EM_Progress_h245Address">--
--<OSS.FIELDNAME 
--		H323-MESSAGES.Progress-UUIE.callIdentifier
--		"callIdentifier">--
--<OSS.FIELDNAME 
--		H323-MESSAGES.Progress-UUIE.h245SecurityMode
--		"h245SecurityMode">--
--<OSS.DefineName
--		H323-MESSAGES.Progress-UUIE.h245SecurityMode
--		"EM_Progress_h245SecurityMode">--
--<OSS.FIELDNAME 
--		H323-MESSAGES.Progress-UUIE.tokens
--		"tokens">--
--<OSS.DefineName
--		H323-MESSAGES.Progress-UUIE.tokens
--		"EM_Progress_tokens">--
--<OSS.FIELDNAME 
--		H323-MESSAGES.Progress-UUIE.cryptoTokens
--		"cryptoTokens">--
--<OSS.DefineName
--		H323-MESSAGES.Progress-UUIE.cryptoTokens
--		"EM_Progress_cryptoTokens">--
--<OSS.FIELDNAME 
--		H323-MESSAGES.Progress-UUIE.fastStart
--		"fastStart">--
--<OSS.DefineName
--		H323-MESSAGES.Progress-UUIE.fastStart
--		"EM_Progress_fastStart">--

-- ------------------------------------------------------------- --
-- IP ::= OCTET STRING (SIZE(4))
-- ------------------------------------------------------------- --

--<ASN1.PDU
--		H323-MESSAGES.IP>--
--<OSS.TYPENAME 
--		H323-MESSAGES.IP
--		"EmIP">--

-- ------------------------------------------------------------- --
-- TransportAddress ::= CHOICE
-- {
-- 	ipAddress 		SEQUENCE
-- 	{
-- 		ip			IP,
-- 		port		INTEGER(0..65535)
-- 	},
-- 	ipSourceRoute 	SEQUENCE
-- 	{
-- 		ip			IP,
-- 		port		INTEGER(0..65535),
-- 		route		SEQUENCE OF IP,
-- 		routing 	CHOICE
-- 		{
-- 			strict	NULL,
-- 			loose	NULL,
-- 			...
-- 		},
-- 		...
-- 	},
-- 	ipxAddress 		SEQUENCE
-- 	{
-- 		node		OCTET STRING (SIZE(6)),
-- 		netnum		OCTET STRING (SIZE(4)),
-- 		port		OCTET STRING (SIZE(2))
-- 	},
-- 	ip6Address 		SEQUENCE
-- 	{
-- 		ip			OCTET STRING (SIZE(16)),
-- 		port		INTEGER(0..65535),
-- 		...
-- 	},
-- 	netBios			OCTET STRING (SIZE(16)),
-- 	nsap			OCTET STRING (SIZE(1..20)),
-- 	nonStandardAddress	NonStandardParameter,	
-- 	...	
-- }
-- ------------------------------------------------------------- --

--<ASN1.PDU
--		H323-MESSAGES.TransportAddress>--
--<OSS.TYPENAME 
--		H323-MESSAGES.TransportAddress 
--		"EmH225TransportAddress">--

--<OSS.InlineType 
--		H323-MESSAGES.TransportAddress.ipAddress>--
--<OSS.TYPENAME 
--		H323-MESSAGES.TransportAddress.ipAddress 
--		"EmIPAddress">--
--<OSS.FIELDNAME 
--		H323-MESSAGES.TransportAddress.ipAddress
--		"ipAddress">--
--<OSS.DefineName
--		H323-MESSAGES.TransportAddress.ipAddress
--		"EM_ipAddress">--
--<OSS.FIELDNAME 
--		H323-MESSAGES.TransportAddress.ipAddress.ip
--		"ip">--
--<OSS.FIELDNAME 
--		H323-MESSAGES.TransportAddress.ipAddress.port
--		"port">--

--<OSS.InlineType 
--		H323-MESSAGES.TransportAddress.ipSourceRoute>--
--<OSS.TYPENAME 
--		H323-MESSAGES.TransportAddress.ipSourceRoute 
--		"EmIPSourceRoute">--
--<OSS.FIELDNAME 
--		H323-MESSAGES.TransportAddress.ipSourceRoute
--		"ipSourceRoute">--
--<OSS.DefineName
--		H323-MESSAGES.TransportAddress.ipSourceRoute
--		"EM_ipSourceRoute">--
--<OSS.FIELDNAME 
--		H323-MESSAGES.TransportAddress.ipSourceRoute.ip
--		"ip">--
--<OSS.FIELDNAME 
--		H323-MESSAGES.TransportAddress.ipSourceRoute.port
--		"port">--
--<OSS.ExtractType
--		H323-MESSAGES.TransportAddress.ipSourceRoute.route>--
--<OSS.TYPENAME
--		H323-MESSAGES.TransportAddress.ipSourceRoute.route
--		"EmSeqOfIP">--
--<OSS.FIELDNAME 
--		H323-MESSAGES.TransportAddress.ipSourceRoute.route
--		"route">--
--<OSS.ExtractType
--		H323-MESSAGES.TransportAddress.ipSourceRoute.routing>--
--<OSS.TYPENAME 
--		H323-MESSAGES.TransportAddress.ipSourceRoute.routing
--		"EmRouting">--
--<OSS.FIELDNAME 
--		H323-MESSAGES.TransportAddress.ipSourceRoute.routing
--		"routing">--
--<OSS.FIELDNAME 
--		H323-MESSAGES.TransportAddress.ipSourceRoute.routing.strict
--		"strict">--
--<OSS.DefineName
--		H323-MESSAGES.TransportAddress.ipSourceRoute.routing.strict
--		"EM_strict">--
--<OSS.FIELDNAME 
--		H323-MESSAGES.TransportAddress.ipSourceRoute.routing.loose
--		"loose">--
--<OSS.DefineName
--		H323-MESSAGES.TransportAddress.ipSourceRoute.routing.loose
--		"EM_loose">--

--<OSS.InlineType 
--		H323-MESSAGES.TransportAddress.ipxAddress>--
--<OSS.TYPENAME 
--		H323-MESSAGES.TransportAddress.ipxAddress
--		"EmIPXAddress">--
--<OSS.FIELDNAME 
--		H323-MESSAGES.TransportAddress.ipxAddress
--		"ipxAddress">--
--<OSS.DefineName
--		H323-MESSAGES.TransportAddress.ipxAddress
--		"EM_ipxAddress">--
--<OSS.InlineType
--		H323-MESSAGES.TransportAddress.ipxAddress.node>--
--<OSS.TYPENAME
--		H323-MESSAGES.TransportAddress.ipxAddress.node
--		"EmIPXNode">--
--<OSS.FIELDNAME 
--		H323-MESSAGES.TransportAddress.ipxAddress.node
--		"node">--
--<OSS.InlineType
--		H323-MESSAGES.TransportAddress.ipxAddress.netnum>--
--<OSS.TYPENAME
--		H323-MESSAGES.TransportAddress.ipxAddress.netnum
--		"EmIPXNetnum">--
--<OSS.FIELDNAME 
--		H323-MESSAGES.TransportAddress.ipxAddress.netnum
--		"netnum">--
--<OSS.InlineType
--		H323-MESSAGES.TransportAddress.ipxAddress.port>--
--<OSS.TYPENAME
--		H323-MESSAGES.TransportAddress.ipxAddress.port
--		"EmIPXPort">--
--<OSS.FIELDNAME 
--		H323-MESSAGES.TransportAddress.ipxAddress.port
--		"port">--

--<OSS.InlineType 
--		H323-MESSAGES.TransportAddress.ip6Address>--
--<OSS.TYPENAME 
--		H323-MESSAGES.TransportAddress.ip6Address 
--		"EmIP6Address">--
--<OSS.FIELDNAME 
--		H323-MESSAGES.TransportAddress.ip6Address
--		"ip6Address">--
--<OSS.DefineName
--		H323-MESSAGES.TransportAddress.ip6Address
--		"EM_ip6Address">--
--<OSS.InlineType 
--		H323-MESSAGES.TransportAddress.ip6Address.ip>--
--<OSS.TYPENAME 
--		H323-MESSAGES.TransportAddress.ip6Address.ip 
--		"EmIP6">--
--<OSS.FIELDNAME 
--		H323-MESSAGES.TransportAddress.ip6Address.ip
--		"ip">--
--<OSS.FIELDNAME 
--		H323-MESSAGES.TransportAddress.ip6Address.port
--		"port">--

--<OSS.InlineType 
--		H323-MESSAGES.TransportAddress.netBios>--
--<OSS.TYPENAME 
--		H323-MESSAGES.TransportAddress.netBios 
--		"EmNetBios">--
--<OSS.FIELDNAME 
--		H323-MESSAGES.TransportAddress.netBios
--		"netBios">--
--<OSS.DefineName
--		H323-MESSAGES.TransportAddress.netBios
--		"EM_netBios">--

--<OSS.TYPENAME 
--		H323-MESSAGES.TransportAddress.nsap 
--		"EmNSAP">--
--<OSS.InlineType 
--		H323-MESSAGES.TransportAddress.nsap>--
--<OSS.FIELDNAME 
--		H323-MESSAGES.TransportAddress.nsap
--		"nsap">--
--<OSS.DefineName
--		H323-MESSAGES.TransportAddress.nsap
--		"EM_nsap">--

--<OSS.FIELDNAME 
--		H323-MESSAGES.TransportAddress.nonStandardAddress
--		"nonStandardAddress">--
--<OSS.DefineName
--		H323-MESSAGES.TransportAddress.nonStandardAddress
--		"EM_nonStandardAddress">--


-- ------------------------------------------------------------- --
-- EndpointType ::= SEQUENCE
-- {
-- 	nonStandardData	NonStandardParameter OPTIONAL,
-- 	vendor			VendorIdentifier OPTIONAL,
-- 	gatekeeper		GatekeeperInfo OPTIONAL,
-- 	gateway			GatewayInfo OPTIONAL,
-- 	mcu				McuInfo OPTIONAL,
-- 	terminal		TerminalInfo OPTIONAL,
-- 	mc				BOOLEAN,
-- 	undefinedNode	BOOLEAN,	
-- 	...
-- }
-- ------------------------------------------------------------- --

--<ASN1.PDU
--		H323-MESSAGES.EndpointType>--
--<OSS.TYPENAME 
--		H323-MESSAGES.EndpointType 
--		"EmEndpointType">--
--<OSS.FIELDNAME 
--		H323-MESSAGES.EndpointType.nonStandardData
--		"nonStandardData">--
--<OSS.DefineName
--		H323-MESSAGES.EndpointType.nonStandardData
--		"EM_EndpointType_nonStandardData">--
--<OSS.FIELDNAME 
--		H323-MESSAGES.EndpointType.vendor
--		"vendor">--
--<OSS.DefineName
--		H323-MESSAGES.EndpointType.vendor
--		"EM_vendor">--
--<OSS.FIELDNAME 
--		H323-MESSAGES.EndpointType.gatekeeper
--		"gatekeeper">--
--<OSS.DefineName
--		H323-MESSAGES.EndpointType.gatekeeper
--		"EM_gatekeeper">--
--<OSS.FIELDNAME 
--		H323-MESSAGES.EndpointType.gateway
--		"gateway">--
--<OSS.DefineName
--		H323-MESSAGES.EndpointType.gateway
--		"EM_gateway">--
--<OSS.FIELDNAME 
--		H323-MESSAGES.EndpointType.mcu
--		"mcu">--
--<OSS.DefineName
--		H323-MESSAGES.EndpointType.mcu
--		"EM_mcu">--
--<OSS.FIELDNAME 
--		H323-MESSAGES.EndpointType.terminal
--		"terminal">--
--<OSS.DefineName
--		H323-MESSAGES.EndpointType.terminal
--		"EM_terminal">--
--<OSS.FIELDNAME 
--		H323-MESSAGES.EndpointType.mc
--		"mc">--
--<OSS.FIELDNAME 
--		H323-MESSAGES.EndpointType.undefinedNode
--		"undefinedNode">--

-- ------------------------------------------------------------- --
-- GatewayInfo ::= SEQUENCE
-- {
-- 	protocol		SEQUENCE OF SupportedProtocols OPTIONAL,
-- 	nonStandardData	NonStandardParameter OPTIONAL,
-- 	...
-- }
-- ------------------------------------------------------------- --

--<ASN1.PDU
--		H323-MESSAGES.GatewayInfo>--
--<OSS.TYPENAME 
--		H323-MESSAGES.GatewayInfo 
--		"EmGatewayInfo">--
--<OSS.FIELDNAME 
--		H323-MESSAGES.GatewayInfo.protocol
--		"protocol">--
--<OSS.DefineName
--		H323-MESSAGES.GatewayInfo.protocol
--		"EM_protocol">--
--<OSS.FIELDNAME 
--		H323-MESSAGES.GatewayInfo.nonStandardData
--		"nonStandardData">--
--<OSS.DefineName
--		H323-MESSAGES.GatewayInfo.nonStandardData
--		"EM_GatewayInfo_nonStandardData">--

-- ------------------------------------------------------------- --
-- SupportedProtocols ::= CHOICE
-- {
-- 	nonStandardData	NonStandardParameter,
-- 	h310			H310Caps,
-- 	h320			H320Caps,
-- 	h321			H321Caps,
-- 	h322			H322Caps,
-- 	h323			H323Caps,
-- 	h324			H324Caps,
-- 	voice			VoiceCaps,
-- 	t120-only		T120OnlyCaps,
-- 	...,
-- 	nonStandardProtocol	NonStandardProtocol
-- }
-- ------------------------------------------------------------- --

--<ASN1.PDU
--		H323-MESSAGES.SupportedProtocols>--
--<OSS.TYPENAME 
--		H323-MESSAGES.SupportedProtocols
--		"EmSupportedProtocols">--
--<OSS.FIELDNAME 
--		H323-MESSAGES.SupportedProtocols.nonStandardData
--		"nonStandardData">--
--<OSS.DefineName
--		H323-MESSAGES.SupportedProtocols.nonStandardData
--		"EM_nonStandardData">--
--<OSS.FIELDNAME 
--		H323-MESSAGES.SupportedProtocols.h310
--		"h310">--
--<OSS.DefineName
--		H323-MESSAGES.SupportedProtocols.h310
--		"EM_h310">--
--<OSS.FIELDNAME 
--		H323-MESSAGES.SupportedProtocols.h320
--		"h320">--
--<OSS.DefineName
--		H323-MESSAGES.SupportedProtocols.h320
--		"EM_h320">--
--<OSS.FIELDNAME 
--		H323-MESSAGES.SupportedProtocols.h321
--		"h321">--
--<OSS.DefineName
--		H323-MESSAGES.SupportedProtocols.h321
--		"EM_h321">--
--<OSS.FIELDNAME 
--		H323-MESSAGES.SupportedProtocols.h322
--		"h322">--
--<OSS.DefineName
--		H323-MESSAGES.SupportedProtocols.h322
--		"EM_h322">--
--<OSS.FIELDNAME 
--		H323-MESSAGES.SupportedProtocols.h323
--		"h323">--
--<OSS.DefineName
--		H323-MESSAGES.SupportedProtocols.h323
--		"EM_h323">--
--<OSS.FIELDNAME 
--		H323-MESSAGES.SupportedProtocols.h324
--		"h324">--
--<OSS.DefineName
--		H323-MESSAGES.SupportedProtocols.h324
--		"EM_h324">--
--<OSS.FIELDNAME 
--		H323-MESSAGES.SupportedProtocols.voice
--		"voice">--
--<OSS.DefineName
--		H323-MESSAGES.SupportedProtocols.voice
--		"EM_voice">--
--<OSS.FIELDNAME 
--		H323-MESSAGES.SupportedProtocols.t120-only
--		"t120_only">--
--<OSS.DefineName
--		H323-MESSAGES.SupportedProtocols.t120-only
--		"EM_t120_only">--
--<OSS.FIELDNAME 
--		H323-MESSAGES.SupportedProtocols.nonStandardProtocol
--		"nonStandardProtocol">--
--<OSS.DefineName
--		H323-MESSAGES.SupportedProtocols.nonStandardProtocol
--		"EM_nonStandardProtocol">--

-- ------------------------------------------------------------- --
-- H310Caps ::= SEQUENCE
-- {
-- 	nonStandardData	NonStandardParameter OPTIONAL,
-- 	...,
-- 	dataRatesSupported	SEQUENCE OF DataRate OPTIONAL,
-- 	supportedPrefixes	SEQUENCE OF SupportedPrefix 
-- }
-- ------------------------------------------------------------- --

--<ASN1.PDU
--		H323-MESSAGES.H310Caps>--
--<OSS.TYPENAME 
--		H323-MESSAGES.H310Caps
--		"EmH310Caps">--
--<OSS.FIELDNAME 
--		H323-MESSAGES.H310Caps.nonStandardData
--		"nonStandardData">--
--<OSS.DefineName
--		H323-MESSAGES.H310Caps.nonStandardData
--		"EM_H310_nonStandardData">--
--<OSS.FIELDNAME 
--		H323-MESSAGES.H310Caps.dataRatesSupported
--		"dataRatesSupported">--
--<OSS.DefineName
--		H323-MESSAGES.H310Caps.dataRatesSupported
--		"EM_H310_dataRatesSupported">--
--<OSS.FIELDNAME 
--		H323-MESSAGES.H310Caps.supportedPrefixes
--		"supportedPrefixes">--
--<OSS.DefineName
--		H323-MESSAGES.H310Caps.supportedPrefixes
--		"EM_H310_supportedPrefixes">--

-- ------------------------------------------------------------- --
-- H320Caps ::= SEQUENCE
-- {
-- 	nonStandardData	NonStandardParameter OPTIONAL,
-- 	...,
-- 	dataRatesSupported	SEQUENCE OF DataRate OPTIONAL,
-- 	supportedPrefixes	SEQUENCE OF SupportedPrefix  
-- }
-- ------------------------------------------------------------- --

--<ASN1.PDU
--		H323-MESSAGES.H320Caps>--
--<OSS.TYPENAME 
--		H323-MESSAGES.H320Caps
--		"EmH320Caps">--
--<OSS.FIELDNAME 
--		H323-MESSAGES.H320Caps.nonStandardData
--		"nonStandardData">--
--<OSS.DefineName
--		H323-MESSAGES.H320Caps.nonStandardData
--		"EM_H320_nonStandardData">--
--<OSS.FIELDNAME 
--		H323-MESSAGES.H320Caps.dataRatesSupported
--		"dataRatesSupported">--
--<OSS.DefineName
--		H323-MESSAGES.H320Caps.dataRatesSupported
--		"EM_H320_dataRatesSupported">--
--<OSS.FIELDNAME 
--		H323-MESSAGES.H320Caps.supportedPrefixes
--		"supportedPrefixes">--
--<OSS.DefineName
--		H323-MESSAGES.H320Caps.supportedPrefixes
--		"EM_H320_supportedPrefixes">--

-- ------------------------------------------------------------- --
-- H321Caps ::= SEQUENCE
-- {
-- 	nonStandardData	NonStandardParameter OPTIONAL,
-- 	...,
-- 	dataRatesSupported	SEQUENCE OF DataRate OPTIONAL,
-- 	supportedPrefixes	SEQUENCE OF SupportedPrefix 
-- }
-- ------------------------------------------------------------- --

--<ASN1.PDU
--		H323-MESSAGES.H321Caps>--
--<OSS.TYPENAME 
--		H323-MESSAGES.H321Caps
--		"EmH321Caps">--
--<OSS.FIELDNAME 
--		H323-MESSAGES.H321Caps.nonStandardData
--		"nonStandardData">--
--<OSS.DefineName
--		H323-MESSAGES.H321Caps.nonStandardData
--		"EM_H321_nonStandardData">--
--<OSS.FIELDNAME 
--		H323-MESSAGES.H321Caps.dataRatesSupported
--		"dataRatesSupported">--
--<OSS.DefineName
--		H323-MESSAGES.H321Caps.dataRatesSupported
--		"EM_H321_dataRatesSupported">--
--<OSS.FIELDNAME 
--		H323-MESSAGES.H321Caps.supportedPrefixes
--		"supportedPrefixes">--
--<OSS.DefineName
--		H323-MESSAGES.H321Caps.supportedPrefixes
--		"EM_H321_supportedPrefixes">--

-- ------------------------------------------------------------- --
-- H322Caps ::= SEQUENCE
-- {
-- 	nonStandardData	NonStandardParameter OPTIONAL,
-- 	...,
-- 	dataRatesSupported	SEQUENCE OF DataRate OPTIONAL,
-- 	supportedPrefixes	SEQUENCE OF SupportedPrefix  
-- }
-- ------------------------------------------------------------- --

--<ASN1.PDU
--		H323-MESSAGES.H322Caps>--
--<OSS.TYPENAME 
--		H323-MESSAGES.H322Caps
--		"EmH322Caps">--
--<OSS.FIELDNAME 
--		H323-MESSAGES.H322Caps.nonStandardData
--		"nonStandardData">--
--<OSS.DefineName
--		H323-MESSAGES.H322Caps.nonStandardData
--		"EM_H322_nonStandardData">--
--<OSS.FIELDNAME 
--		H323-MESSAGES.H322Caps.dataRatesSupported
--		"dataRatesSupported">--
--<OSS.DefineName
--		H323-MESSAGES.H322Caps.dataRatesSupported
--		"EM_H322_dataRatesSupported">--
--<OSS.FIELDNAME 
--		H323-MESSAGES.H322Caps.supportedPrefixes
--		"supportedPrefixes">--
--<OSS.DefineName
--		H323-MESSAGES.H322Caps.supportedPrefixes
--		"EM_H322_supportedPrefixes">--

-- ------------------------------------------------------------- --
-- H323Caps ::= SEQUENCE
-- {
-- 	nonStandardData	NonStandardParameter OPTIONAL,
-- 	...,
-- 	dataRatesSupported	SEQUENCE OF DataRate OPTIONAL,
-- 	supportedPrefixes	SEQUENCE OF SupportedPrefix 
-- }
-- ------------------------------------------------------------- --

--<ASN1.PDU
--		H323-MESSAGES.H323Caps>--
--<OSS.TYPENAME 
--		H323-MESSAGES.H323Caps
--		"EmH323Caps">--
--<OSS.FIELDNAME 
--		H323-MESSAGES.H323Caps.nonStandardData
--		"nonStandardData">--
--<OSS.DefineName
--		H323-MESSAGES.H323Caps.nonStandardData
--		"EM_H323_nonStandardData">--
--<OSS.FIELDNAME 
--		H323-MESSAGES.H323Caps.dataRatesSupported
--		"dataRatesSupported">--
--<OSS.DefineName
--		H323-MESSAGES.H323Caps.dataRatesSupported
--		"EM_H323_dataRatesSupported">--
--<OSS.FIELDNAME 
--		H323-MESSAGES.H323Caps.supportedPrefixes
--		"supportedPrefixes">--
--<OSS.DefineName
--		H323-MESSAGES.H323Caps.supportedPrefixes
--		"EM_H323_supportedPrefixes">--

-- ------------------------------------------------------------- --
-- H324Caps ::= SEQUENCE
-- {
-- 	nonStandardData	NonStandardParameter OPTIONAL,
-- 	...,
-- 	dataRatesSupported	SEQUENCE OF DataRate OPTIONAL,
-- 	supportedPrefixes	SEQUENCE OF SupportedPrefix 
-- }
-- ------------------------------------------------------------- --

--<ASN1.PDU
--		H323-MESSAGES.H324Caps>--
--<OSS.TYPENAME 
--		H323-MESSAGES.H324Caps
--		"EmH324Caps">--
--<OSS.FIELDNAME 
--		H323-MESSAGES.H324Caps.nonStandardData
--		"nonStandardData">--
--<OSS.DefineName
--		H323-MESSAGES.H324Caps.nonStandardData
--		"EM_H324_nonStandardData">--
--<OSS.FIELDNAME 
--		H323-MESSAGES.H324Caps.dataRatesSupported
--		"dataRatesSupported">--
--<OSS.DefineName
--		H323-MESSAGES.H324Caps.dataRatesSupported
--		"EM_H324_dataRatesSupported">--
--<OSS.FIELDNAME 
--		H323-MESSAGES.H324Caps.supportedPrefixes
--		"supportedPrefixes">--
--<OSS.DefineName
--		H323-MESSAGES.H324Caps.supportedPrefixes
--		"EM_H324_supportedPrefixes">--

-- ------------------------------------------------------------- --
-- VoiceCaps ::= SEQUENCE
-- {
-- 	nonStandardData	NonStandardParameter OPTIONAL,
-- 	...,
-- 	dataRatesSupported	SEQUENCE OF DataRate OPTIONAL,
-- 	supportedPrefixes	SEQUENCE OF SupportedPrefix 
-- }
-- ------------------------------------------------------------- --

--<ASN1.PDU
--		H323-MESSAGES.VoiceCaps>--
--<OSS.TYPENAME 
--		H323-MESSAGES.VoiceCaps
--		"EmVoiceCaps">--
--<OSS.FIELDNAME 
--		H323-MESSAGES.VoiceCaps.nonStandardData
--		"nonStandardData">--
--<OSS.DefineName
--		H323-MESSAGES.VoiceCaps.nonStandardData
--		"EM_Voice_nonStandardData">--
--<OSS.FIELDNAME 
--		H323-MESSAGES.VoiceCaps.dataRatesSupported
--		"dataRatesSupported">--
--<OSS.DefineName
--		H323-MESSAGES.VoiceCaps.dataRatesSupported
--		"EM_Voice_dataRatesSupported">--
--<OSS.FIELDNAME 
--		H323-MESSAGES.VoiceCaps.supportedPrefixes
--		"supportedPrefixes">--
--<OSS.DefineName
--		H323-MESSAGES.VoiceCaps.supportedPrefixes
--		"EM_Voice_supportedPrefixes">--

-- ------------------------------------------------------------- --
-- T120OnlyCaps ::= SEQUENCE
-- {
-- 	nonStandardData	NonStandardParameter OPTIONAL,
-- 	...,
-- 	dataRatesSupported	SEQUENCE OF DataRate OPTIONAL,
-- 	supportedPrefixes	SEQUENCE OF SupportedPrefix 
-- }
-- ------------------------------------------------------------- --

--<ASN1.PDU
--		H323-MESSAGES.T120OnlyCaps>--
--<OSS.TYPENAME 
--		H323-MESSAGES.T120OnlyCaps
--		"EmT120OnlyCaps">--
--<OSS.FIELDNAME 
--		H323-MESSAGES.T120OnlyCaps.nonStandardData
--		"nonStandardData">--
--<OSS.DefineName
--		H323-MESSAGES.T120OnlyCaps.nonStandardData
--		"EM_T120Only_nonStandardData">--
--<OSS.FIELDNAME 
--		H323-MESSAGES.T120OnlyCaps.dataRatesSupported
--		"dataRatesSupported">--
--<OSS.DefineName
--		H323-MESSAGES.T120OnlyCaps.dataRatesSupported
--		"EM_T120Only_dataRatesSupported">--
--<OSS.FIELDNAME 
--		H323-MESSAGES.T120OnlyCaps.supportedPrefixes
--		"supportedPrefixes">--
--<OSS.DefineName
--		H323-MESSAGES.T120OnlyCaps.supportedPrefixes
--		"EM_T120Only_supportedPrefixes">--

-- ------------------------------------------------------------- --
-- NonStandardProtocol ::= SEQUENCE
-- {
-- 	nonStandardData	NonStandardParameter OPTIONAL,
-- 	dataRatesSupported	SEQUENCE OF DataRate OPTIONAL,
-- 	supportedPrefixes	SEQUENCE OF SupportedPrefix,
-- 	...
-- }
-- ------------------------------------------------------------- --

--<ASN1.PDU
--		H323-MESSAGES.NonStandardProtocol>--
--<OSS.TYPENAME 
--		H323-MESSAGES.NonStandardProtocol
--		"EmNonStandardProtocol">--
--<OSS.FIELDNAME 
--		H323-MESSAGES.NonStandardProtocol.nonStandardData
--		"nonStandardData">--
--<OSS.DefineName
--		H323-MESSAGES.NonStandardProtocol.nonStandardData
--		"EM_NonStandardProtocol_nonStandardData">--
--<OSS.FIELDNAME 
--		H323-MESSAGES.NonStandardProtocol.dataRatesSupported
--		"dataRatesSupported">--
--<OSS.DefineName
--		H323-MESSAGES.NonStandardProtocol.dataRatesSupported
--		"EM_NonStandardProtocol_dataRatesSupported">--
--<OSS.FIELDNAME 
--		H323-MESSAGES.NonStandardProtocol.supportedPrefixes
--		"supportedPrefixes">--

-- ------------------------------------------------------------- --
-- McuInfo ::= SEQUENCE
-- {
-- 	nonStandardData	NonStandardParameter OPTIONAL,
-- 	...
-- }
-- ------------------------------------------------------------- --

--<ASN1.PDU
--		H323-MESSAGES.McuInfo>--
--<OSS.TYPENAME 
--		H323-MESSAGES.McuInfo
--		"EmMcuInfo">--
--<OSS.FIELDNAME 
--		H323-MESSAGES.McuInfo.nonStandardData
--		"nonStandardData">--
--<OSS.DefineName
--		H323-MESSAGES.McuInfo.nonStandardData
--		"EM_McuInfo_nonStandardData">--

-- ------------------------------------------------------------- --
-- TerminalInfo ::= SEQUENCE 
-- {
-- 	nonStandardData	NonStandardParameter OPTIONAL,
-- 	...
-- }
-- ------------------------------------------------------------- --

--<ASN1.PDU
--		H323-MESSAGES.TerminalInfo>--
--<OSS.TYPENAME 
--		H323-MESSAGES.TerminalInfo 
--		"EmTerminalInfo">--
--<OSS.FIELDNAME 
--		H323-MESSAGES.TerminalInfo.nonStandardData
--		"nonStandardData">--
--<OSS.DefineName
--		H323-MESSAGES.TerminalInfo.nonStandardData
--		"EM_TerminalInfo_nonStandardData">--

-- ------------------------------------------------------------- --
-- GatekeeperInfo ::= SEQUENCE 
-- {
-- 	nonStandardData	NonStandardParameter OPTIONAL,
-- 	...
-- }
-- ------------------------------------------------------------- --

--<ASN1.PDU
--		H323-MESSAGES.GatekeeperInfo>--
--<OSS.TYPENAME 
--		H323-MESSAGES.GatekeeperInfo 
--		"EmGatekeeperInfo">--
--<OSS.FIELDNAME 
--		H323-MESSAGES.GatekeeperInfo.nonStandardData
--		"nonStandardData">--
--<OSS.DefineName
--		H323-MESSAGES.GatekeeperInfo.nonStandardData
--		"EM_GatekeeperInfo_nonStandardData">--

-- ------------------------------------------------------------- --
-- VendorIdentifier ::= SEQUENCE
-- {
-- 	vendor			H221NonStandard,
-- 	productId		OCTET STRING (SIZE(1..256)) OPTIONAL,
-- 	versionId		OCTET STRING (SIZE(1..256)) OPTIONAL,
-- 	...
-- }
-- ------------------------------------------------------------- --

--<ASN1.PDU
--		H323-MESSAGES.VendorIdentifier>--
--<OSS.TYPENAME 
--		H323-MESSAGES.VendorIdentifier 
--		"EmVendorIdentifier">--
--<OSS.FIELDNAME 
--		H323-MESSAGES.VendorIdentifier.vendor
--		"vendor">--
--<OSS.TYPENAME
--		H323-MESSAGES.VendorIdentifier.productId
--		"EmProductIdString">--
--<OSS.FIELDNAME 
--		H323-MESSAGES.VendorIdentifier.productId
--		"productId">--
--<OSS.DefineName
--		H323-MESSAGES.VendorIdentifier.productId
--		"EM_productId">--
--<OSS.TYPENAME
--		H323-MESSAGES.VendorIdentifier.versionId
--		"EmVersionIdString">--
--<OSS.FIELDNAME 
--		H323-MESSAGES.VendorIdentifier.versionId
--		"versionId">--
--<OSS.DefineName
--		H323-MESSAGES.VendorIdentifier.versionId
--		"EM_versionId">--

-- ------------------------------------------------------------- --
-- H221NonStandard ::= SEQUENCE
-- {	
--  t35CountryCode		INTEGER(0..255),
-- 	t35Extension		INTEGER(0..255),
-- 	manufacturerCode	INTEGER(0..65535),
-- 	...
-- }
-- ------------------------------------------------------------- --

--<ASN1.PDU
--		H323-MESSAGES.H221NonStandard>--
--<OSS.TYPENAME 
--		H323-MESSAGES.H221NonStandard
--		"EmH221NonStandard">--
--<OSS.FIELDNAME 
--		H323-MESSAGES.H221NonStandard.t35CountryCode
--		"t35CountryCode">--
--<OSS.FIELDNAME 
--		H323-MESSAGES.H221NonStandard.t35Extension
--		"t35Extension">--
--<OSS.FIELDNAME 
--		H323-MESSAGES.H221NonStandard.manufacturerCode
--		"manufacturerCode">--

-- ------------------------------------------------------------- --
-- NonStandardParameter ::= SEQUENCE
-- {
-- 	nonStandardIdentifier	NonStandardIdentifier,
-- 	data					OCTET STRING
-- }
-- ------------------------------------------------------------- --

--<ASN1.PDU
--		H323-MESSAGES.NonStandardParameter>--
--<OSS.TYPENAME 
--		H323-MESSAGES.NonStandardParameter 
--		"EmNonStandardParameter">--
--<OSS.FIELDNAME 
--		H323-MESSAGES.NonStandardParameter.nonStandardIdentifier
--		"nonStandardIdentifier">--
--<OSS.FIELDNAME 
--		H323-MESSAGES.NonStandardParameter.data
--		"data">--

-- ------------------------------------------------------------- --
-- NonStandardIdentifier		::=CHOICE
-- {
-- 	object			OBJECT IDENTIFIER,
-- 	h221NonStandard	H221NonStandard,
-- 	...
-- }
-- ------------------------------------------------------------- --

--<ASN1.PDU
--		H323-MESSAGES.NonStandardIdentifier>--
--<OSS.TYPENAME 
--		H323-MESSAGES.NonStandardIdentifier
--		"EmNonStandardIdentifier">--
--<OSS.FIELDNAME 
--		H323-MESSAGES.NonStandardIdentifier.object
--		"object">--
--<OSS.DefineName
--		H323-MESSAGES.NonStandardIdentifier.object
--		"EM_object">--
--<OSS.FIELDNAME 
--		H323-MESSAGES.NonStandardIdentifier.h221NonStandard
--		"h221NonStandard">--
--<OSS.DefineName
--		H323-MESSAGES.NonStandardIdentifier.h221NonStandard
--		"EM_h221NonStandard">--

-- ------------------------------------------------------------- --
-- AliasAddress ::= CHOICE
-- {
-- 	e164		IA5String (SIZE (1..128)) (FROM ("0123456789#*,")),
-- 	h323-ID		BMPString (SIZE (1..256)),
-- 	...,
-- 	url-ID		IA5String (SIZE(1..512)),
-- 	transportID	TransportAddress,
-- 	email-ID	IA5String (SIZE(1..512)),
-- 	partyNumber	PartyNumber 
-- }	
-- ------------------------------------------------------------- --

--<ASN1.PDU
--		H323-MESSAGES.AliasAddress>--
--<OSS.TYPENAME 
--		H323-MESSAGES.AliasAddress 
--		"EmAliasAddress">--
--<OSS.FIELDNAME 
--		H323-MESSAGES.AliasAddress.e164
--		"e164">--
--<OSS.DefineName
--		H323-MESSAGES.AliasAddress.e164
--		"EM_e164">--
--<OSS.ExtractType
--		H323-MESSAGES.AliasAddress.h323-ID>--
--<OSS.TYPENAME
--		H323-MESSAGES.AliasAddress.h323-ID
--		"EmH323ID">--
--<OSS.FIELDNAME 
--		H323-MESSAGES.AliasAddress.h323-ID
--		"h323_ID">--
--<OSS.DefineName
--		H323-MESSAGES.AliasAddress.h323-ID
--		"EM_h323_ID">--
--<OSS.FIELDNAME 
--		H323-MESSAGES.AliasAddress.url-ID
--		"url_ID">--
--<OSS.DefineName
--		H323-MESSAGES.AliasAddress.url-ID
--		"EM_url_ID">--
--<OSS.NULLTERM
--		H323-MESSAGES.AliasAddress.url-ID>--
--<OSS.FIELDNAME 
--		H323-MESSAGES.AliasAddress.transportID
--		"transportID">--
--<OSS.DefineName
--		H323-MESSAGES.AliasAddress.transportID
--		"EM_transportID">--
--<OSS.FIELDNAME 
--		H323-MESSAGES.AliasAddress.email-ID
--		"email_ID">--
--<OSS.DefineName
--		H323-MESSAGES.AliasAddress.email-ID
--		"EM_email_ID">--
--<OSS.NULLTERM
--		H323-MESSAGES.AliasAddress.email-ID>--
--<OSS.FIELDNAME 
--		H323-MESSAGES.AliasAddress.partyNumber
--		"partyNumber">--
--<OSS.DefineName
--		H323-MESSAGES.AliasAddress.partyNumber
--		"EM_partyNumber">--

-- ------------------------------------------------------------- --
-- PartyNumber ::= CHOICE
-- {
-- 	publicNumber 					PublicPartyNumber,
-- 	dataPartyNumber 				NumberDigits,
-- 	telexPartyNumber 				NumberDigits,
-- 	privateNumber 					PrivatePartyNumber,
-- 	nationalStandardPartyNumber 	NumberDigits,
-- 	...
-- }
-- ------------------------------------------------------------- --

--<ASN1.PDU
--		H323-MESSAGES.PartyNumber>--
--<OSS.TYPENAME 
--		H323-MESSAGES.PartyNumber
--		"EmPartyNumber">--
--<OSS.FIELDNAME 
--		H323-MESSAGES.PartyNumber.publicNumber
--		"publicNumber">--
--<OSS.DefineName
--		H323-MESSAGES.PartyNumber.publicNumber
--		"EM_publicNumber">--
--<OSS.FIELDNAME 
--		H323-MESSAGES.PartyNumber.dataPartyNumber
--		"dataPartyNumber">--
--<OSS.DefineName
--		H323-MESSAGES.PartyNumber.dataPartyNumber
--		"EM_dataPartyNumber">--
--<OSS.FIELDNAME 
--		H323-MESSAGES.PartyNumber.telexPartyNumber
--		"telexPartyNumber">--
--<OSS.DefineName
--		H323-MESSAGES.PartyNumber.telexPartyNumber
--		"EM_telexPartyNumber">--
--<OSS.FIELDNAME 
--		H323-MESSAGES.PartyNumber.privateNumber
--		"privateNumber">--
--<OSS.DefineName
--		H323-MESSAGES.PartyNumber.privateNumber
--		"EM_privateNumber">--
--<OSS.FIELDNAME 
--		H323-MESSAGES.PartyNumber.nationalStandardPartyNumber
--		"nationalStandardPartyNumber">--
--<OSS.DefineName
--		H323-MESSAGES.PartyNumber.nationalStandardPartyNumber
--		"EM_nationalStandardPartyNumber">--

-- ------------------------------------------------------------- --
-- PublicPartyNumber ::= SEQUENCE
-- {
-- 	publicTypeOfNumber	PublicTypeOfNumber,
-- 	publicNumberDigits	NumberDigits
-- }
-- ------------------------------------------------------------- --

--<ASN1.PDU
--		H323-MESSAGES.PublicPartyNumber>--
--<OSS.TYPENAME 
--		H323-MESSAGES.PublicPartyNumber 
--		"EmPublicPartyNumber">--
--<OSS.FIELDNAME 
--		H323-MESSAGES.PublicPartyNumber.publicTypeOfNumber
--		"publicTypeOfNumber">--
--<OSS.FIELDNAME 
--		H323-MESSAGES.PublicPartyNumber.publicNumberDigits
--		"publicNumberDigits">--

-- ------------------------------------------------------------- --
-- PrivatePartyNumber ::= SEQUENCE
-- {
-- 	privateTypeOfNumber	PrivateTypeOfNumber,
-- 	privateNumberDigits	NumberDigits
-- }
-- ------------------------------------------------------------- --

--<ASN1.PDU
--		H323-MESSAGES.PrivatePartyNumber>--
--<OSS.TYPENAME 
--		H323-MESSAGES.PrivatePartyNumber 
--		"EmPrivatePartyNumber">--
--<OSS.FIELDNAME 
--		H323-MESSAGES.PrivatePartyNumber.privateTypeOfNumber
--		"privateTypeOfNumber">--
--<OSS.FIELDNAME 
--		H323-MESSAGES.PrivatePartyNumber.privateNumberDigits
--		"privateNumberDigits">--

-- ------------------------------------------------------------- --
-- NumberDigits ::= IA5String (SIZE (1..128)) (FROM ("0123456789#*,"))
-- ------------------------------------------------------------- --

--<ASN1.PDU 
--		H323-MESSAGES.NumberDigits>--
--<OSS.TYPENAME 
--		H323-MESSAGES.NumberDigits 
--		"EmNumberDigits">--

-- ------------------------------------------------------------- --
-- PublicTypeOfNumber ::= CHOICE
-- {
-- 	unknown					NULL,
-- 	internationalNumber		NULL,
-- 	nationalNumber			NULL,
-- 	networkSpecificNumber	NULL,
-- 	subscriberNumber		NULL,
-- 	abbreviatedNumber		NULL,
-- 	...
-- }
-- ------------------------------------------------------------- --

--<ASN1.PDU
--		H323-MESSAGES.PublicTypeOfNumber>--
--<OSS.TYPENAME 
--		H323-MESSAGES.PublicTypeOfNumber
--		"EmPublicTypeOfNumber">--
--<OSS.FIELDNAME 
--		H323-MESSAGES.PublicTypeOfNumber.unknown
--		"unknown">--
--<OSS.DefineName
--		H323-MESSAGES.PublicTypeOfNumber.unknown
--		"EM_PublicTypeOfNumber_unknown">--
--<OSS.FIELDNAME 
--		H323-MESSAGES.PublicTypeOfNumber.internationalNumber
--		"internationalNumber">--
--<OSS.DefineName
--		H323-MESSAGES.PublicTypeOfNumber.internationalNumber
--		"EM_internationalNumber">--
--<OSS.FIELDNAME 
--		H323-MESSAGES.PublicTypeOfNumber.nationalNumber
--		"nationalNumber">--
--<OSS.DefineName
--		H323-MESSAGES.PublicTypeOfNumber.nationalNumber
--		"EM_nationalNumber">--
--<OSS.FIELDNAME 
--		H323-MESSAGES.PublicTypeOfNumber.networkSpecificNumber
--		"networkSpecificNumber">--
--<OSS.DefineName
--		H323-MESSAGES.PublicTypeOfNumber.networkSpecificNumber
--		"EM_networkSpecificNumber">--
--<OSS.FIELDNAME 
--		H323-MESSAGES.PublicTypeOfNumber.subscriberNumber
--		"subscriberNumber">--
--<OSS.DefineName
--		H323-MESSAGES.PublicTypeOfNumber.subscriberNumber
--		"EM_subscriberNumber">--
--<OSS.FIELDNAME 
--		H323-MESSAGES.PublicTypeOfNumber.abbreviatedNumber
--		"abbreviatedNumber">--
--<OSS.DefineName
--		H323-MESSAGES.PublicTypeOfNumber.abbreviatedNumber
--		"EM_PublicTypeOfNumber_abbreviatedNumber">--

-- ------------------------------------------------------------- --
-- PrivateTypeOfNumber ::= CHOICE
-- {
-- 	unknown					NULL,
-- 	level2RegionalNumber	NULL,
-- 	level1RegionalNumber	NULL,
-- 	pISNSpecificNumber		NULL,
-- 	localNumber				NULL,
-- 	abbreviatedNumber		NULL,
-- 	...
-- }
-- ------------------------------------------------------------- --

--<ASN1.PDU
--		H323-MESSAGES.PrivateTypeOfNumber>--
--<OSS.TYPENAME 
--		H323-MESSAGES.PrivateTypeOfNumber
--		"EmPrivateTypeOfNumber">--
--<OSS.FIELDNAME 
--		H323-MESSAGES.PrivateTypeOfNumber.unknown
--		"unknown">--
--<OSS.DefineName
--		H323-MESSAGES.PrivateTypeOfNumber.unknown
--		"EM_PrivateTypeOfNumber_unknown">--
--<OSS.FIELDNAME 
--		H323-MESSAGES.PrivateTypeOfNumber.level2RegionalNumber
--		"level2RegionalNumber">--
--<OSS.DefineName
--		H323-MESSAGES.PrivateTypeOfNumber.level2RegionalNumber
--		"EM_level2RegionalNumber">--
--<OSS.FIELDNAME 
--		H323-MESSAGES.PrivateTypeOfNumber.level1RegionalNumber
--		"level1RegionalNumber">--
--<OSS.DefineName
--		H323-MESSAGES.PrivateTypeOfNumber.level1RegionalNumber
--		"EM_level1RegionalNumber">--
--<OSS.FIELDNAME 
--		H323-MESSAGES.PrivateTypeOfNumber.pISNSpecificNumber
--		"pISNSpecificNumber">--
--<OSS.DefineName
--		H323-MESSAGES.PrivateTypeOfNumber.pISNSpecificNumber
--		"EM_pISNSpecificNumber">--
--<OSS.FIELDNAME 
--		H323-MESSAGES.PrivateTypeOfNumber.localNumber
--		"localNumber">--
--<OSS.DefineName
--		H323-MESSAGES.PrivateTypeOfNumber.localNumber
--		"EM_localNumber">--
--<OSS.FIELDNAME 
--		H323-MESSAGES.PrivateTypeOfNumber.abbreviatedNumber
--		"abbreviatedNumber">--
--<OSS.DefineName
--		H323-MESSAGES.PrivateTypeOfNumber.abbreviatedNumber
--		"EM_PrivateTypeOfNumber_abbreviatedNumber">--

-- ------------------------------------------------------------- --
-- Endpoint ::= SEQUENCE
-- { 
-- 	nonStandardData			NonStandardParameter OPTIONAL, 
-- 	aliasAddress			SEQUENCE OF AliasAddress OPTIONAL,  
-- 	callSignalAddress		SEQUENCE OF TransportAddress OPTIONAL,  
-- 	rasAddress				SEQUENCE OF TransportAddress OPTIONAL,  
-- 	endpointType			EndpointType OPTIONAL,  
-- 	tokens					SEQUENCE OF ClearToken OPTIONAL,  
-- 	cryptoTokens			SEQUENCE OF CryptoH323Token OPTIONAL,
-- 	priority				INTEGER(0..127) OPTIONAL, 
-- 	remoteExtensionAddress	SEQUENCE OF AliasAddress OPTIONAL,
-- 	destExtraCallInfo		SEQUENCE OF AliasAddress OPTIONAL,
-- 	...
-- } 
-- ------------------------------------------------------------- --

--<ASN1.PDU
--		H323-MESSAGES.Endpoint>--
--<OSS.TYPENAME 
--		H323-MESSAGES.Endpoint
--		"EmEndpoint">--
--<OSS.FIELDNAME 
--		H323-MESSAGES.Endpoint.nonStandardData
--		"nonStandardData">--
--<OSS.DefineName
--		H323-MESSAGES.Endpoint.nonStandardData
--		"EM_Endpoint_nonStandardData">--
--<OSS.FIELDNAME 
--		H323-MESSAGES.Endpoint.aliasAddress
--		"aliasAddress">--
--<OSS.DefineName
--		H323-MESSAGES.Endpoint.aliasAddress
--		"EM_aliasAddress">--
--<OSS.FIELDNAME 
--		H323-MESSAGES.Endpoint.callSignalAddress
--		"callSignalAddress">--
--<OSS.DefineName
--		H323-MESSAGES.Endpoint.callSignalAddress
--		"EM_Endpoint_callSignalAddress">--
--<OSS.FIELDNAME 
--		H323-MESSAGES.Endpoint.rasAddress
--		"rasAddress">--
--<OSS.DefineName
--		H323-MESSAGES.Endpoint.rasAddress
--		"EM_rasAddress">--
--<OSS.FIELDNAME 
--		H323-MESSAGES.Endpoint.endpointType
--		"endpointType">--
--<OSS.DefineName
--		H323-MESSAGES.Endpoint.endpointType
--		"EM_endpointType">--
--<OSS.FIELDNAME 
--		H323-MESSAGES.Endpoint.tokens
--		"tokens">--
--<OSS.DefineName
--		H323-MESSAGES.Endpoint.tokens
--		"EM_Endpoint_tokens">--
--<OSS.FIELDNAME 
--		H323-MESSAGES.Endpoint.cryptoTokens
--		"cryptoTokens">--
--<OSS.DefineName
--		H323-MESSAGES.Endpoint.cryptoTokens
--		"EM_Endpoint_cryptoTokens">--
--<OSS.FIELDNAME 
--		H323-MESSAGES.Endpoint.priority
--		"priority">--
--<OSS.DefineName
--		H323-MESSAGES.Endpoint.priority
--		"EM_priority">--
--<OSS.FIELDNAME 
--		H323-MESSAGES.Endpoint.remoteExtensionAddress
--		"remoteExtensionAddress">--
--<OSS.DefineName
--		H323-MESSAGES.Endpoint.remoteExtensionAddress
--		"EM_Endpoint_remoteExtensionAddress">--
--<OSS.FIELDNAME 
--		H323-MESSAGES.Endpoint.destExtraCallInfo
--		"destExtraCallInfo">--
--<OSS.DefineName
--		H323-MESSAGES.Endpoint.destExtraCallInfo
--		"EM_Endpoint_destExtraCallInfo">--

-- ------------------------------------------------------------- --
-- AlternateGK ::= SEQUENCE
-- {
-- 	rasAddress				TransportAddress,
-- 	gatekeeperIdentifier	GatekeeperIdentifier OPTIONAL,
-- 	needToRegister			BOOLEAN,
-- 	priority				INTEGER (0..127),
-- 	...
-- }
-- ------------------------------------------------------------- --

--<ASN1.PDU
--		H323-MESSAGES.AlternateGK>--
--<OSS.TYPENAME 
--		H323-MESSAGES.AlternateGK
--		"EmAlternateGK">--
--<OSS.FIELDNAME 
--		H323-MESSAGES.AlternateGK.rasAddress
--		"rasAddress">--
--<OSS.FIELDNAME 
--		H323-MESSAGES.AlternateGK.gatekeeperIdentifier
--		"gatekeeperIdentifier">--
--<OSS.DefineName
--		H323-MESSAGES.AlternateGK.gatekeeperIdentifier
--		"EM_AlternateGK_gatekeeperIdentifier">--
--<OSS.FIELDNAME 
--		H323-MESSAGES.AlternateGK.needToRegister
--		"needToRegister">--
--<OSS.FIELDNAME 
--		H323-MESSAGES.AlternateGK.priority
--		"priority">--

-- ------------------------------------------------------------- --
-- AltGKInfo ::= SEQUENCE
-- {
-- 	alternateGatekeeper	SEQUENCE OF AlternateGK,
-- 	altGKisPermanent	BOOLEAN,
-- 	...
-- }
-- ------------------------------------------------------------- --

--<ASN1.PDU
--		H323-MESSAGES.AltGKInfo>--
--<OSS.TYPENAME 
--		H323-MESSAGES.AltGKInfo
--		"EmAltGKInfo">--
--<OSS.FIELDNAME 
--		H323-MESSAGES.AltGKInfo.alternateGatekeeper
--		"alternateGatekeeper">--
--<OSS.FIELDNAME 
--		H323-MESSAGES.AltGKInfo.altGKisPermanent
--		"altGKisPermanent">--

-- ------------------------------------------------------------- --
-- SecurityServiceMode ::= CHOICE 
-- {
-- 	nonStandard		NonStandardParameter,
-- 	none			NULL,
-- 	default			NULL,
-- 	...	
-- }
-- ------------------------------------------------------------- --

--<ASN1.PDU
--		H323-MESSAGES.SecurityServiceMode>--
--<OSS.TYPENAME 
--		H323-MESSAGES.SecurityServiceMode
--		"EmSecurityServiceMode">--
--<OSS.FIELDNAME 
--		H323-MESSAGES.SecurityServiceMode.nonStandard
--		"nonStandard">--
--<OSS.DefineName
--		H323-MESSAGES.SecurityServiceMode.nonStandard
--		"EM_SecurityServiceMode_nonStandard">--
--<OSS.FIELDNAME 
--		H323-MESSAGES.SecurityServiceMode.none
--		"none">--
--<OSS.DefineName
--		H323-MESSAGES.SecurityServiceMode.none
--		"EM_none">--
--<OSS.FIELDNAME 
--		H323-MESSAGES.SecurityServiceMode.default
--		"defaultMode">--
--<OSS.DefineName
--		H323-MESSAGES.SecurityServiceMode.default
--		"EM_defaultMode">--

-- ------------------------------------------------------------- --
-- SecurityCapabilities ::= SEQUENCE 
-- {
-- 	nonStandard			NonStandardParameter OPTIONAL,
-- 	encryption			SecurityServiceMode,
-- 	authenticaton		SecurityServiceMode,
-- 	integrity			SecurityServiceMode,
-- 	...
-- }
-- ------------------------------------------------------------- --

--<ASN1.PDU
--		H323-MESSAGES.SecurityCapabilities>--
--<OSS.TYPENAME 
--		H323-MESSAGES.SecurityCapabilities
--		"EmSecurityCapabilities">--
--<OSS.FIELDNAME 
--		H323-MESSAGES.SecurityCapabilities.nonStandard
--		"nonStandard">--
--<OSS.DefineName
--		H323-MESSAGES.SecurityCapabilities.nonStandard
--		"EM_SecurityCapabilities_nonStandard">--
--<OSS.FIELDNAME 
--		H323-MESSAGES.SecurityCapabilities.encryption
--		"encryption">--
--<OSS.FIELDNAME 
--		H323-MESSAGES.SecurityCapabilities.authenticaton
--		"authenticaton">--
--<OSS.FIELDNAME 
--		H323-MESSAGES.SecurityCapabilities.integrity
--		"integrity">--

-- ------------------------------------------------------------- --
-- H245Security ::= CHOICE 
-- {
-- 	nonStandard		NonStandardParameter,
-- 	noSecurity		NULL,
-- 	tls				SecurityCapabilities,
-- 	ipsec			SecurityCapabilities,
-- 	...
-- }
-- ------------------------------------------------------------- --

--<ASN1.PDU
--		H323-MESSAGES.H245Security>--
--<OSS.TYPENAME 
--		H323-MESSAGES.H245Security
--		"EmH245Security">--
--<OSS.FIELDNAME 
--		H323-MESSAGES.H245Security.nonStandard
--		"nonStandard">--
--<OSS.DefineName
--		H323-MESSAGES.H245Security.nonStandard
--		"EM_H245Security_nonStandard">--
--<OSS.FIELDNAME 
--		H323-MESSAGES.H245Security.noSecurity
--		"noSecurity">--
--<OSS.DefineName
--		H323-MESSAGES.H245Security.noSecurity
--		"EM_noSecurity">--
--<OSS.FIELDNAME 
--		H323-MESSAGES.H245Security.tls
--		"tls">--
--<OSS.DefineName
--		H323-MESSAGES.H245Security.tls
--		"EM_H245Security_tls">--
--<OSS.FIELDNAME 
--		H323-MESSAGES.H245Security.ipsec
--		"ipsec">--
--<OSS.DefineName
--		H323-MESSAGES.H245Security.ipsec
--		"EM_H245Security_ipsec">--

-- ------------------------------------------------------------- --
-- QseriesOptions ::= SEQUENCE
-- {
-- 	q932Full	BOOLEAN,
-- 	q951Full	BOOLEAN,
-- 	q952Full	BOOLEAN,
-- 	q953Full	BOOLEAN,
-- 	q955Full	BOOLEAN,
-- 	q956Full	BOOLEAN,
-- 	q957Full	BOOLEAN,
-- 	q954Info	Q954Details,	
-- 	...
-- }
-- ------------------------------------------------------------- --

--<ASN1.PDU
--		H323-MESSAGES.QseriesOptions>--
--<OSS.TYPENAME 
--		H323-MESSAGES.QseriesOptions
--		"EmQseriesOptions">--
--<OSS.FIELDNAME 
--		H323-MESSAGES.QseriesOptions.q932Full
--		"q932Full">--
--<OSS.FIELDNAME 
--		H323-MESSAGES.QseriesOptions.q951Full
--		"q951Full">--
--<OSS.FIELDNAME 
--		H323-MESSAGES.QseriesOptions.q952Full
--		"q952Full">--
--<OSS.FIELDNAME 
--		H323-MESSAGES.QseriesOptions.q953Full
--		"q953Full">--
--<OSS.FIELDNAME 
--		H323-MESSAGES.QseriesOptions.q955Full
--		"q955Full">--
--<OSS.FIELDNAME 
--		H323-MESSAGES.QseriesOptions.q956Full
--		"q956Full">--
--<OSS.FIELDNAME 
--		H323-MESSAGES.QseriesOptions.q957Full
--		"q957Full">--
--<OSS.FIELDNAME 
--		H323-MESSAGES.QseriesOptions.q954Info
--		"q954Info">--

-- ------------------------------------------------------------- --
-- Q954Details ::= SEQUENCE
-- {
-- 	conferenceCalling	BOOLEAN,
-- 	threePartyService	BOOLEAN,
-- 	...
-- }
-- ------------------------------------------------------------- --

--<ASN1.PDU
--		H323-MESSAGES.Q954Details>--
--<OSS.TYPENAME 
--		H323-MESSAGES.Q954Details
--		"EmQ954Details">--
--<OSS.FIELDNAME 
--		H323-MESSAGES.Q954Details.conferenceCalling
--		"conferenceCalling">--
--<OSS.FIELDNAME 
--		H323-MESSAGES.Q954Details.threePartyService
--		"threePartyService">--


-- ------------------------------------------------------------- --
-- GloballyUniqueID		::=	OCTET STRING (SIZE(16))
-- ConferenceIdentifier	::=	GloballyUniqueID
-- ------------------------------------------------------------- --

--<ASN1.PDU
--		H323-MESSAGES.GloballyUniqueID>--
--<OSS.TYPENAME 
--		H323-MESSAGES.GloballyUniqueID
--		"EmGloballyUniqueID">--
--<OSS.TYPENAME
--		H323-MESSAGES.ConferenceIdentifier
--		"EmConferenceIdentifier">--

-- ------------------------------------------------------------- --
-- RequestSeqNum			::=	INTEGER (1..65535)
-- ------------------------------------------------------------- --

--<OSS.TYPENAME 
--		H323-MESSAGES.RequestSeqNum
--		"EmRequestSeqNum">--

-- ------------------------------------------------------------- --
-- GatekeeperIdentifier	::=	BMPString (SIZE(1..128))
-- ------------------------------------------------------------- --

--<ASN1.PDU
--		H323-MESSAGES.GatekeeperIdentifier>--
--<OSS.TYPENAME 
--		H323-MESSAGES.GatekeeperIdentifier
--		"EmGatekeeperIdentifier">--

-- ------------------------------------------------------------- --
-- BandWidth				::=	INTEGER (0.. 4294967295)
-- ------------------------------------------------------------- --

--<OSS.TYPENAME 
--		H323-MESSAGES.BandWidth
--		"EmBandWidth">--

-- ------------------------------------------------------------- --
-- CallReferenceValue		::=	INTEGER (0..65535)
-- ------------------------------------------------------------- --

--<OSS.TYPENAME 
--		H323-MESSAGES.CallReferenceValue
--		"EmCallReferenceValue">--

-- ------------------------------------------------------------- --
-- EndpointIdentifier		::=	BMPString (SIZE(1..128))
-- ------------------------------------------------------------- --

--<ASN1.PDU
--		H323-MESSAGES.EndpointIdentifier>--
--<OSS.TYPENAME 
--		H323-MESSAGES.EndpointIdentifier
--		"EmEndpointIdentifier">--

-- ------------------------------------------------------------- --
-- ProtocolIdentifier		::=	OBJECT IDENTIFIER
-- ------------------------------------------------------------- --

--<OSS.TYPENAME 
--		H323-MESSAGES.ProtocolIdentifier
--		"EmProtocolIdentifier">--

-- ------------------------------------------------------------- --
-- TimeToLive				::=	INTEGER (1..4294967295)
-- ------------------------------------------------------------- --

--<OSS.TYPENAME
--		H323-MESSAGES.TimeToLive
--		"EmTimeToLive">--

-- ------------------------------------------------------------- --
-- CallIdentifier ::= SEQUENCE
-- {
-- 	guid		GloballyUniqueID,
-- 	...
-- }
-- 
-- ------------------------------------------------------------- --

--<ASN1.PDU
--		H323-MESSAGES.CallIdentifier>--
--<OSS.TYPENAME 
--		H323-MESSAGES.CallIdentifier 
--		"EmCallIdentifier">--
--<OSS.FIELDNAME 
--		H323-MESSAGES.CallIdentifier.guid
--		"guid">--

-- ------------------------------------------------------------- --
-- EncryptIntAlg ::= CHOICE
-- {	
-- 	nonStandard			NonStandardParameter,
-- 	isoAlgorithm		OBJECT IDENTIFIER,
-- 	...
-- }
-- ------------------------------------------------------------- --

--<ASN1.PDU
--		H323-MESSAGES.EncryptIntAlg>--
--<OSS.TYPENAME 
--		H323-MESSAGES.EncryptIntAlg
--		"EmEncryptIntAlg">--
--<OSS.FIELDNAME 
--		H323-MESSAGES.EncryptIntAlg.nonStandard
--		"nonStandard">--
--<OSS.DefineName
--		H323-MESSAGES.EncryptIntAlg.nonStandard
--		"EM_EncryptIntAlg_nonStandard">--
--<OSS.FIELDNAME 
--		H323-MESSAGES.EncryptIntAlg.isoAlgorithm
--		"isoAlgorithm">--
--<OSS.DefineName
--		H323-MESSAGES.EncryptIntAlg.isoAlgorithm
--		"EM_isoAlgorithm">--

-- ------------------------------------------------------------- --
-- NonIsoIntegrityMechanism ::= CHOICE
-- {
-- 	hMAC-MD5				NULL,
-- 	hMAC-iso10118-2-s		EncryptIntAlg,	
-- 	hMAC-iso10118-2-l		EncryptIntAlg,	
-- 	hMAC-iso10118-3			OBJECT IDENTIFIER,  
-- }
-- ------------------------------------------------------------- --

--<ASN1.PDU
--		H323-MESSAGES.NonIsoIntegrityMechanism>--
--<OSS.TYPENAME 
--		H323-MESSAGES.NonIsoIntegrityMechanism
--		"EmNonIsoIntegrityMechanism">--
--<OSS.FIELDNAME 
--		H323-MESSAGES.NonIsoIntegrityMechanism.hMAC-MD5
--		"hMAC_MD5">--
--<OSS.DefineName
--		H323-MESSAGES.NonIsoIntegrityMechanism.hMAC-MD5
--		"EM_hMAC_MD5">--
--<OSS.FIELDNAME 
--		H323-MESSAGES.NonIsoIntegrityMechanism.hMAC-iso10118-2-s
--		"hMAC_iso10118_2_s">--
--<OSS.DefineName
--		H323-MESSAGES.NonIsoIntegrityMechanism.hMAC-iso10118-2-s
--		"EM_hMAC_iso10118_2_s">--
--<OSS.FIELDNAME 
--		H323-MESSAGES.NonIsoIntegrityMechanism.hMAC-iso10118-2-l
--		"hMAC_iso10118_2_l">--
--<OSS.DefineName
--		H323-MESSAGES.NonIsoIntegrityMechanism.hMAC-iso10118-2-l
--		"EM_hMAC_iso10118_2_l">--
--<OSS.FIELDNAME 
--		H323-MESSAGES.NonIsoIntegrityMechanism.hMAC-iso10118-3
--		"hMAC_iso10118_3">--
--<OSS.DefineName
--		H323-MESSAGES.NonIsoIntegrityMechanism.hMAC-iso10118-3
--		"EM_hMAC_iso10118_3">--

-- ------------------------------------------------------------- --
-- IntegrityMechanism ::= CHOICE
-- {
-- 	nonStandard				NonStandardParameter,
-- 	digSig					NULL,	
-- 	iso9797					OBJECT IDENTIFIER,	
-- 	nonIsoIM				NonIsoIntegrityMechanism,
-- 	...
-- }
-- ------------------------------------------------------------- --

--<ASN1.PDU
--		H323-MESSAGES.IntegrityMechanism>--
--<OSS.TYPENAME 
--		H323-MESSAGES.IntegrityMechanism
--		"EmIntegrityMechanism">--
--<OSS.FIELDNAME 
--		H323-MESSAGES.IntegrityMechanism.nonStandard
--		"nonStandard">--
--<OSS.DefineName
--		H323-MESSAGES.IntegrityMechanism.nonStandard
--		"EM_IntegrityMechanism_nonStandard">--
--<OSS.FIELDNAME 
--		H323-MESSAGES.IntegrityMechanism.digSig
--		"digSig">--
--<OSS.DefineName
--		H323-MESSAGES.IntegrityMechanism.digSig
--		"EM_digSig">--
--<OSS.FIELDNAME 
--		H323-MESSAGES.IntegrityMechanism.iso9797
--		"mechIso9797">--
--<OSS.DefineName
--		H323-MESSAGES.IntegrityMechanism.iso9797
--		"EM_mechIso9797">--
--<OSS.FIELDNAME 
--		H323-MESSAGES.IntegrityMechanism.nonIsoIM
--		"nonIsoIM">--
--<OSS.DefineName
--		H323-MESSAGES.IntegrityMechanism.nonIsoIM
--		"EM_nonIsoIM">--

-- ------------------------------------------------------------- --
-- ICV ::= SEQUENCE
-- {
-- 	algorithmOID	OBJECT IDENTIFIER,  
-- 	icv				BitString,
-- 	...
-- }
-- ------------------------------------------------------------- --

--<ASN1.PDU
--		H323-MESSAGES.ICV>--
--<OSS.TYPENAME 
--		H323-MESSAGES.ICV
--		"EmICV">--
--<OSS.FIELDNAME 
--		H323-MESSAGES.ICV.algorithmOID
--		"algorithmOID">--
--<OSS.TYPENAME
--		H323-MESSAGES.ICV.icv
--		"EmBitString">--
--<OSS.FIELDNAME 
--		H323-MESSAGES.ICV.icv
--		"icv">--

-- ------------------------------------------------------------- --
-- FastStartToken ::= ClearToken (WITH COMPONENTS {..., timeStamp PRESENT, dhkey PRESENT, generalID PRESENT // set to 'alias' // })
-- ------------------------------------------------------------- --

--<ASN1.PDU
--		H323-MESSAGES.FastStartToken>--
--<OSS.TYPENAME
--		H323-MESSAGES.FastStartToken
--		"EmFastStartToken">--

-- ------------------------------------------------------------- --
-- EncodedFastStartToken ::= TYPE-IDENTIFIER.&Type (FastStartToken)
-- ------------------------------------------------------------- --

--<OSS.TYPENAME
--		H323-MESSAGES.EncodedFastStartToken
--		"EmEncodedFastStartToken">--

-- ------------------------------------------------------------- --
-- HashedEncodedPwdCertToken ::= HASHED 
-- { 
-- 	EncodedPwdCertToken
-- }
-- ------------------------------------------------------------- --

--<ASN1.PDU
--		H323-MESSAGES.HashedEncodedPwdCertToken>--
--<OSS.TYPENAME 
--		H323-MESSAGES.HashedEncodedPwdCertToken
--		"EmHashedEncodedPwdCertToken">--
--<OSS.FIELDNAME
--		H323-MESSAGES.HashedEncodedPwdCertToken.algorithmOID
--		"algorithmOID">--
--<OSS.FIELDNAME
--		H323-MESSAGES.HashedEncodedPwdCertToken.paramS
--		"paramS">--
--<OSS.TYPENAME
--		H323-MESSAGES.HashedEncodedPwdCertToken.hash
--		"EmBitString">--
--<OSS.FIELDNAME
--		H323-MESSAGES.HashedEncodedPwdCertToken.hash
--		"hash">--

-- ------------------------------------------------------------- --
-- EncryptedEncodedPwdCertToken ::= ENCRYPTED
-- { 
-- 	EncodedPwdCertToken
-- }
-- ------------------------------------------------------------- --

--<ASN1.PDU
--		H323-MESSAGES.EncryptedEncodedPwdCertToken>--
--<OSS.TYPENAME 
--		H323-MESSAGES.EncryptedEncodedPwdCertToken
--		"EmEncryptedEncodedPwdCertToken">--
--<OSS.FIELDNAME
--		H323-MESSAGES.EncryptedEncodedPwdCertToken.algorithmOID
--		"algorithmOID">--
--<OSS.FIELDNAME
--		H323-MESSAGES.EncryptedEncodedPwdCertToken.paramS
--		"paramS">--
--<OSS.TYPENAME
--		H323-MESSAGES.EncryptedEncodedPwdCertToken.encryptedData
--		"EmOctetString">--
--<OSS.FIELDNAME
--		H323-MESSAGES.EncryptedEncodedPwdCertToken.encryptedData
--		"encryptedData">--

-- ------------------------------------------------------------- --
-- SignedEncodedPwdCertToken ::= SIGNED 
-- { 
-- 	EncodedPwdCertToken 
-- }
-- ------------------------------------------------------------- --

--<ASN1.PDU
--		H323-MESSAGES.SignedEncodedPwdCertToken>--
--<OSS.TYPENAME 
--		H323-MESSAGES.SignedEncodedPwdCertToken
--		"EmSignedEncodedPwdCertToken">--
--<OSS.FIELDNAME
--		H323-MESSAGES.SignedEncodedPwdCertToken.toBeSigned
--		"toBeSigned">--
--<OSS.FIELDNAME
--		H323-MESSAGES.SignedEncodedPwdCertToken.algorithmOID
--		"algorithmOID">--
--<OSS.FIELDNAME
--		H323-MESSAGES.SignedEncodedPwdCertToken.paramS
--		"paramS">--
--<OSS.TYPENAME
--		H323-MESSAGES.SignedEncodedPwdCertToken.signature
--		"EmBitString">--
--<OSS.FIELDNAME
--		H323-MESSAGES.SignedEncodedPwdCertToken.signature
--		"signature">--

-- ------------------------------------------------------------- --
-- SignedEncodedFastStartToken ::= SIGNED 
-- { 
-- 	EncodedFastStartToken 
-- }
-- ------------------------------------------------------------- --

--<ASN1.PDU
--		H323-MESSAGES.SignedEncodedFastStartToken>--
--<OSS.TYPENAME 
--		H323-MESSAGES.SignedEncodedFastStartToken
--		"EmSignedEncodedFastStartToken">--
--<OSS.FIELDNAME
--		H323-MESSAGES.SignedEncodedFastStartToken.toBeSigned
--		"toBeSigned">--
--<OSS.FIELDNAME
--		H323-MESSAGES.SignedEncodedFastStartToken.algorithmOID
--		"algorithmOID">--
--<OSS.FIELDNAME
--		H323-MESSAGES.SignedEncodedFastStartToken.paramS
--		"paramS">--
--<OSS.TYPENAME
--		H323-MESSAGES.SignedEncodedFastStartToken.signature
--		"EmBitString">--
--<OSS.FIELDNAME
--		H323-MESSAGES.SignedEncodedFastStartToken.signature
--		"signature">--

-- ------------------------------------------------------------- --
-- CryptoH323Token ::= CHOICE
-- {
-- 	cryptoEPPwdHash		SEQUENCE
-- 	{
-- 		alias			AliasAddress, 	
-- 		timeStamp		TimeStamp, 						
-- 		token 			HashedEncodedPwdCertToken
-- 	},
-- 	
-- 	cryptoGKPwdHash  	SEQUENCE
-- 	{
-- 		gatekeeperId	GatekeeperIdentifier,	
-- 		timeStamp		TimeStamp, 							
-- 		token			HashedEncodedPwdCertToken
-- 	},
-- 	
-- 	cryptoEPPwdEncr		EncryptedEncodedPwdCertToken,
-- 	cryptoGKPwdEncr		EncryptedEncodedPwdCertToken,
-- 	
-- 	cryptoEPCert 		SignedEncodedPwdCertToken,
-- 	cryptoGKCert 		SignedEncodedPwdCertToken,
-- 	
-- 	cryptoFastStart		SignedEncodedFastStartToken,
-- 	
-- 	nestedcryptoToken	CryptoToken,
-- 	...
-- }
-- ------------------------------------------------------------- --

--<ASN1.PDU
--		H323-MESSAGES.CryptoH323Token>--
--<OSS.TYPENAME 
--		H323-MESSAGES.CryptoH323Token
--		"EmCryptoH323Token">--

--<OSS.InlineType
--		H323-MESSAGES.CryptoH323Token.cryptoEPPwdHash>--
--<OSS.TYPENAME
--		H323-MESSAGES.CryptoH323Token.cryptoEPPwdHash
--		"EmCryptoEPPwdHash">--
--<OSS.FIELDNAME 
--		H323-MESSAGES.CryptoH323Token.cryptoEPPwdHash
--		"cryptoEPPwdHash">--
--<OSS.DefineName
--		H323-MESSAGES.CryptoH323Token.cryptoEPPwdHash
--		"EM_cryptoEPPwdHash">--
--<OSS.FIELDNAME
--		H323-MESSAGES.CryptoH323Token.cryptoEPPwdHash.alias
--		"alias">--
--<OSS.FIELDNAME
--		H323-MESSAGES.CryptoH323Token.cryptoEPPwdHash.timeStamp
--		"timeStamp">--
--<OSS.FIELDNAME
--		H323-MESSAGES.CryptoH323Token.cryptoEPPwdHash.token
--		"token">--

--<OSS.InlineType
--		H323-MESSAGES.CryptoH323Token.cryptoGKPwdHash>--
--<OSS.TYPENAME
--		H323-MESSAGES.CryptoH323Token.cryptoGKPwdHash
--		"EmCryptoGKPwdHash">--
--<OSS.FIELDNAME 
--		H323-MESSAGES.CryptoH323Token.cryptoGKPwdHash
--		"cryptoGKPwdHash">--
--<OSS.DefineName
--		H323-MESSAGES.CryptoH323Token.cryptoGKPwdHash
--		"EM_cryptoGKPwdHash">--
--<OSS.FIELDNAME
--		H323-MESSAGES.CryptoH323Token.cryptoGKPwdHash.gatekeeperId
--		"gatekeeperId">--
--<OSS.FIELDNAME
--		H323-MESSAGES.CryptoH323Token.cryptoGKPwdHash.timeStamp
--		"timeStamp">--
--<OSS.ExtractType
--		H323-MESSAGES.CryptoH323Token.cryptoGKPwdHash.token>--

--<OSS.FIELDNAME 
--		H323-MESSAGES.CryptoH323Token.cryptoEPPwdEncr
--		"cryptoEPPwdEncr">--
--<OSS.DefineName
--		H323-MESSAGES.CryptoH323Token.cryptoEPPwdEncr
--		"EM_cryptoEPPwdEncr">--

--<OSS.FIELDNAME 
--		H323-MESSAGES.CryptoH323Token.cryptoGKPwdEncr
--		"cryptoGKPwdEncr">--
--<OSS.DefineName
--		H323-MESSAGES.CryptoH323Token.cryptoGKPwdEncr
--		"EM_cryptoGKPwdEncr">--

--<OSS.FIELDNAME 
--		H323-MESSAGES.CryptoH323Token.cryptoEPCert
--		"cryptoEPCert">--
--<OSS.DefineName
--		H323-MESSAGES.CryptoH323Token.cryptoEPCert
--		"EM_cryptoEPCert">--

--<OSS.FIELDNAME 
--		H323-MESSAGES.CryptoH323Token.cryptoGKCert
--		"cryptoGKCert">--
--<OSS.DefineName
--		H323-MESSAGES.CryptoH323Token.cryptoGKCert
--		"EM_cryptoGKCert">--

--<OSS.FIELDNAME 
--		H323-MESSAGES.CryptoH323Token.cryptoFastStart
--		"cryptoFastStart">--
--<OSS.DefineName
--		H323-MESSAGES.CryptoH323Token.cryptoFastStart
--		"EM_cryptoFastStart">--

--<OSS.FIELDNAME 
--		H323-MESSAGES.CryptoH323Token.nestedcryptoToken
--		"nestedcryptoToken">--
--<OSS.DefineName
--		H323-MESSAGES.CryptoH323Token.nestedcryptoToken
--		"EM_nestedcryptoToken">--

-- ------------------------------------------------------------- --
-- DataRate ::= SEQUENCE
-- {
-- 	nonStandardData		NonStandardParameter OPTIONAL,
-- 	channelRate			BandWidth,
-- 	channelMultiplier	INTEGER (1..256) OPTIONAL,
-- 	...
-- }
-- ------------------------------------------------------------- --

--<ASN1.PDU
--		H323-MESSAGES.DataRate>--
--<OSS.TYPENAME 
--		H323-MESSAGES.DataRate
--		"EmDataRate">--
--<OSS.FIELDNAME 
--		H323-MESSAGES.DataRate.nonStandardData
--		"nonStandardData">--
--<OSS.DefineName
--		H323-MESSAGES.DataRate.nonStandardData
--		"EM_DataRate_nonStandardData">--
--<OSS.FIELDNAME 
--		H323-MESSAGES.DataRate.channelRate
--		"channelRate">--
--<OSS.FIELDNAME 
--		H323-MESSAGES.DataRate.channelMultiplier
--		"channelMultiplier">--
--<OSS.DefineName
--		H323-MESSAGES.DataRate.channelMultiplier
--		"EM_channelMultiplier">--

-- ------------------------------------------------------------- --
-- SupportedPrefix ::= SEQUENCE
-- {
-- 	nonStandardData		NonStandardParameter OPTIONAL,
-- 	prefix				AliasAddress,
-- 	...
-- }
-- ------------------------------------------------------------- --

--<ASN1.PDU
--		H323-MESSAGES.SupportedPrefix>--
--<OSS.TYPENAME 
--		H323-MESSAGES.SupportedPrefix
--		"EmSupportedPrefix">--
--<OSS.FIELDNAME 
--		H323-MESSAGES.SupportedPrefix.nonStandardData
--		"nonStandardData">--
--<OSS.DefineName
--		H323-MESSAGES.SupportedPrefix.nonStandardData
--		"EM_SupportedPrefix_nonStandardData">--
--<OSS.FIELDNAME 
--		H323-MESSAGES.SupportedPrefix.prefix
--		"prefix">--

-- ------------------------------------------------------------- --
-- RasMessage ::= CHOICE   
-- {
-- 	gatekeeperRequest			GatekeeperRequest,
-- 	gatekeeperConfirm			GatekeeperConfirm,
-- 	gatekeeperReject			GatekeeperReject,
-- 	registrationRequest			RegistrationRequest,
-- 	registrationConfirm			RegistrationConfirm,
-- 	registrationReject			RegistrationReject,
-- 	unregistrationRequest		UnregistrationRequest,
-- 	unregistrationConfirm		UnregistrationConfirm,
-- 	unregistrationReject		UnregistrationReject,
-- 	admissionRequest			AdmissionRequest,
-- 	admissionConfirm			AdmissionConfirm,
-- 	admissionReject				AdmissionReject,
-- 	bandwidthRequest			BandwidthRequest,
-- 	bandwidthConfirm			BandwidthConfirm,
-- 	bandwidthReject				BandwidthReject,
-- 	disengageRequest			DisengageRequest,
-- 	disengageConfirm			DisengageConfirm,
-- 	disengageReject				DisengageReject,
-- 	locationRequest				LocationRequest,
-- 	locationConfirm				LocationConfirm,
-- 	locationReject				LocationReject,
-- 	infoRequest					InfoRequest,
-- 	infoRequestResponse			InfoRequestResponse,
-- 	nonStandardMessage			NonStandardMessage,
-- 	unknownMessageResponse		UnknownMessageResponse,
-- 	...,
-- 	requestInProgress			RequestInProgress,
-- 	resourcesAvailableIndicate	ResourcesAvailableIndicate,
-- 	resourcesAvailableConfirm	ResourcesAvailableConfirm,
-- 	infoRequestAck				InfoRequestAck,
-- 	infoRequestNak				InfoRequestNak
-- }
-- ------------------------------------------------------------- --

--<ASN1.PDU
--		H323-MESSAGES.RasMessage>--
--<OSS.TYPENAME 
--		H323-MESSAGES.RasMessage
--		"EmRasMessage">--
--<OSS.FIELDNAME 
--		H323-MESSAGES.RasMessage.gatekeeperRequest
--		"grq">--
--<OSS.DefineName
--		H323-MESSAGES.RasMessage.gatekeeperRequest
--		"EM_grq">--
--<OSS.FIELDNAME 
--		H323-MESSAGES.RasMessage.gatekeeperConfirm
--		"gcf">--
--<OSS.DefineName
--		H323-MESSAGES.RasMessage.gatekeeperConfirm
--		"EM_gcf">--
--<OSS.FIELDNAME 
--		H323-MESSAGES.RasMessage.gatekeeperReject
--		"grj">--
--<OSS.DefineName
--		H323-MESSAGES.RasMessage.gatekeeperReject
--		"EM_grj">--
--<OSS.FIELDNAME 
--		H323-MESSAGES.RasMessage.registrationRequest
--		"rrq">--
--<OSS.DefineName
--		H323-MESSAGES.RasMessage.registrationRequest
--		"EM_rrq">--
--<OSS.FIELDNAME 
--		H323-MESSAGES.RasMessage.registrationConfirm
--		"rcf">--
--<OSS.DefineName
--		H323-MESSAGES.RasMessage.registrationConfirm
--		"EM_rcf">--
--<OSS.FIELDNAME 
--		H323-MESSAGES.RasMessage.registrationReject
--		"rrj">--
--<OSS.DefineName
--		H323-MESSAGES.RasMessage.registrationReject
--		"EM_rrj">--
--<OSS.FIELDNAME 
--		H323-MESSAGES.RasMessage.unregistrationRequest
--		"urq">--
--<OSS.DefineName
--		H323-MESSAGES.RasMessage.unregistrationRequest
--		"EM_urq">--
--<OSS.FIELDNAME 
--		H323-MESSAGES.RasMessage.unregistrationConfirm
--		"ucf">--
--<OSS.DefineName
--		H323-MESSAGES.RasMessage.unregistrationConfirm
--		"EM_ucf">--
--<OSS.FIELDNAME 
--		H323-MESSAGES.RasMessage.unregistrationReject
--		"urj">--
--<OSS.DefineName
--		H323-MESSAGES.RasMessage.unregistrationReject
--		"EM_urj">--
--<OSS.FIELDNAME 
--		H323-MESSAGES.RasMessage.admissionRequest
--		"arq">--
--<OSS.DefineName
--		H323-MESSAGES.RasMessage.admissionRequest
--		"EM_arq">--
--<OSS.FIELDNAME 
--		H323-MESSAGES.RasMessage.admissionConfirm
--		"acf">--
--<OSS.DefineName
--		H323-MESSAGES.RasMessage.admissionConfirm
--		"EM_acf">--
--<OSS.FIELDNAME 
--		H323-MESSAGES.RasMessage.admissionReject
--		"arj">--
--<OSS.DefineName
--		H323-MESSAGES.RasMessage.admissionReject
--		"EM_arj">--
--<OSS.FIELDNAME 
--		H323-MESSAGES.RasMessage.bandwidthRequest
--		"brq">--
--<OSS.DefineName
--		H323-MESSAGES.RasMessage.bandwidthRequest
--		"EM_brq">--
--<OSS.FIELDNAME 
--		H323-MESSAGES.RasMessage.bandwidthConfirm
--		"bcf">--
--<OSS.DefineName
--		H323-MESSAGES.RasMessage.bandwidthConfirm
--		"EM_bcf">--
--<OSS.FIELDNAME 
--		H323-MESSAGES.RasMessage.bandwidthReject
--		"brj">--
--<OSS.DefineName
--		H323-MESSAGES.RasMessage.bandwidthReject
--		"EM_brj">--
--<OSS.FIELDNAME 
--		H323-MESSAGES.RasMessage.disengageRequest
--		"drq">--
--<OSS.DefineName
--		H323-MESSAGES.RasMessage.disengageRequest
--		"EM_drq">--
--<OSS.FIELDNAME 
--		H323-MESSAGES.RasMessage.disengageConfirm
--		"dcf">--
--<OSS.DefineName
--		H323-MESSAGES.RasMessage.disengageConfirm
--		"EM_dcf">--
--<OSS.FIELDNAME 
--		H323-MESSAGES.RasMessage.disengageReject
--		"drj">--
--<OSS.DefineName
--		H323-MESSAGES.RasMessage.disengageReject
--		"EM_drj">--
--<OSS.FIELDNAME 
--		H323-MESSAGES.RasMessage.locationRequest
--		"lrq">--
--<OSS.DefineName
--		H323-MESSAGES.RasMessage.locationRequest
--		"EM_lrq">--
--<OSS.FIELDNAME 
--		H323-MESSAGES.RasMessage.locationConfirm
--		"lcf">--
--<OSS.DefineName
--		H323-MESSAGES.RasMessage.locationConfirm
--		"EM_lcf">--
--<OSS.FIELDNAME 
--		H323-MESSAGES.RasMessage.locationReject
--		"lrj">--
--<OSS.DefineName
--		H323-MESSAGES.RasMessage.locationReject
--		"EM_lrj">--
--<OSS.FIELDNAME 
--		H323-MESSAGES.RasMessage.infoRequest
--		"irq">--
--<OSS.DefineName
--		H323-MESSAGES.RasMessage.infoRequest
--		"EM_irq">--
--<OSS.FIELDNAME 
--		H323-MESSAGES.RasMessage.infoRequestResponse
--		"irr">--
--<OSS.DefineName
--		H323-MESSAGES.RasMessage.infoRequestResponse
--		"EM_irr">--
--<OSS.FIELDNAME 
--		H323-MESSAGES.RasMessage.nonStandardMessage
--		"nsm">--
--<OSS.DefineName
--		H323-MESSAGES.RasMessage.nonStandardMessage
--		"EM_nsm">--
--<OSS.FIELDNAME 
--		H323-MESSAGES.RasMessage.unknownMessageResponse
--		"xrs">--
--<OSS.DefineName
--		H323-MESSAGES.RasMessage.unknownMessageResponse
--		"EM_xrs">--
--<OSS.FIELDNAME 
--		H323-MESSAGES.RasMessage.requestInProgress
--		"rip">--
--<OSS.DefineName
--		H323-MESSAGES.RasMessage.requestInProgress
--		"EM_rip">--
--<OSS.FIELDNAME 
--		H323-MESSAGES.RasMessage.resourcesAvailableIndicate
--		"rai">--
--<OSS.DefineName
--		H323-MESSAGES.RasMessage.resourcesAvailableIndicate
--		"EM_rai">--
--<OSS.FIELDNAME 
--		H323-MESSAGES.RasMessage.resourcesAvailableConfirm
--		"rac">--
--<OSS.DefineName
--		H323-MESSAGES.RasMessage.resourcesAvailableConfirm
--		"EM_rac">--
--<OSS.FIELDNAME 
--		H323-MESSAGES.RasMessage.infoRequestAck
--		"iack">--
--<OSS.DefineName
--		H323-MESSAGES.RasMessage.infoRequestAck
--		"EM_iack">--
--<OSS.FIELDNAME 
--		H323-MESSAGES.RasMessage.infoRequestNak
--		"inak">--
--<OSS.DefineName
--		H323-MESSAGES.RasMessage.infoRequestNak
--		"EM_inak">--

-- ------------------------------------------------------------- --
-- GatekeeperRequest ::= SEQUENCE
-- {
-- 	requestSeqNum				RequestSeqNum,
-- 	protocolIdentifier			ProtocolIdentifier,
-- 	nonStandardData				NonStandardParameter OPTIONAL,
-- 	rasAddress					TransportAddress,
-- 	endpointType				EndpointType,
-- 	gatekeeperIdentifier		GatekeeperIdentifier OPTIONAL,
-- 	callServices				QseriesOptions OPTIONAL, 
-- 	endpointAlias				SEQUENCE OF AliasAddress OPTIONAL,
-- 	...,
-- 	alternateEndpoints			SEQUENCE OF Endpoint OPTIONAL,
-- 	tokens						SEQUENCE OF ClearToken OPTIONAL,
-- 	cryptoTokens				SEQUENCE OF CryptoH323Token OPTIONAL,
-- 	authenticationCapability	SEQUENCE OF AuthenticationMechanism OPTIONAL,
-- 	algorithmOIDs				SEQUENCE OF OBJECT IDENTIFIER OPTIONAL,
-- 	integrity					SEQUENCE OF IntegrityMechanism OPTIONAL,
-- 	integrityCheckValue			ICV OPTIONAL
-- }
-- ------------------------------------------------------------- --

--<ASN1.PDU
--		H323-MESSAGES.GatekeeperRequest>--
--<OSS.TYPENAME 
--		H323-MESSAGES.GatekeeperRequest
--		"EmGRQ">--
--<OSS.FIELDNAME 
--		H323-MESSAGES.GatekeeperRequest.requestSeqNum
--		"requestSeqNum">--
--<OSS.FIELDNAME 
--		H323-MESSAGES.GatekeeperRequest.protocolIdentifier
--		"protocolIdentifier">--
--<OSS.FIELDNAME 
--		H323-MESSAGES.GatekeeperRequest.nonStandardData
--		"nonStandardData">--
--<OSS.DefineName
--		H323-MESSAGES.GatekeeperRequest.nonStandardData
--		"EM_GRQ_nonStandardData">--
--<OSS.FIELDNAME 
--		H323-MESSAGES.GatekeeperRequest.rasAddress
--		"rasAddress">--
--<OSS.FIELDNAME 
--		H323-MESSAGES.GatekeeperRequest.endpointType
--		"endpointType">--
--<OSS.FIELDNAME 
--		H323-MESSAGES.GatekeeperRequest.gatekeeperIdentifier
--		"gatekeeperIdentifier">--
--<OSS.DefineName
--		H323-MESSAGES.GatekeeperRequest.gatekeeperIdentifier
--		"EM_GRQ_gatekeeperIdentifier">--
--<OSS.FIELDNAME 
--		H323-MESSAGES.GatekeeperRequest.callServices
--		"callServices">--
--<OSS.DefineName
--		H323-MESSAGES.GatekeeperRequest.callServices
--		"EM_GRQ_callServices">--
--<OSS.FIELDNAME 
--		H323-MESSAGES.GatekeeperRequest.endpointAlias
--		"endpointAlias">--
--<OSS.DefineName
--		H323-MESSAGES.GatekeeperRequest.endpointAlias
--		"EM_GRQ_endpointAlias">--
--<OSS.FIELDNAME 
--		H323-MESSAGES.GatekeeperRequest.alternateEndpoints
--		"alternateEndpoints">--
--<OSS.DefineName
--		H323-MESSAGES.GatekeeperRequest.alternateEndpoints
--		"EM_GRQ_alternateEndpoints">--
--<OSS.FIELDNAME 
--		H323-MESSAGES.GatekeeperRequest.tokens
--		"tokens">--
--<OSS.DefineName
--		H323-MESSAGES.GatekeeperRequest.tokens
--		"EM_GRQ_tokens">--
--<OSS.FIELDNAME 
--		H323-MESSAGES.GatekeeperRequest.cryptoTokens
--		"cryptoTokens">--
--<OSS.DefineName
--		H323-MESSAGES.GatekeeperRequest.cryptoTokens
--		"EM_GRQ_cryptoTokens">--
--<OSS.FIELDNAME 
--		H323-MESSAGES.GatekeeperRequest.authenticationCapability
--		"authenticationCapability">--
--<OSS.DefineName
--		H323-MESSAGES.GatekeeperRequest.authenticationCapability
--		"EM_GRQ_authenticationCapability">--
--<OSS.FIELDNAME 
--		H323-MESSAGES.GatekeeperRequest.algorithmOIDs
--		"algorithmOIDs">--
--<OSS.DefineName
--		H323-MESSAGES.GatekeeperRequest.algorithmOIDs
--		"EM_GRQ_algorithmOIDs">--
--<OSS.FIELDNAME 
--		H323-MESSAGES.GatekeeperRequest.integrity
--		"integrity">--
--<OSS.DefineName
--		H323-MESSAGES.GatekeeperRequest.integrity
--		"EM_GRQ_integrity">--
--<OSS.FIELDNAME 
--		H323-MESSAGES.GatekeeperRequest.integrityCheckValue
--		"integrityCheckValue">--
--<OSS.DefineName
--		H323-MESSAGES.GatekeeperRequest.integrityCheckValue
--		"EM_GRQ_integrityCheckValue">--

-- ------------------------------------------------------------- --
-- GatekeeperConfirm ::= SEQUENCE
-- {
-- 	requestSeqNum			RequestSeqNum,
-- 	protocolIdentifier		ProtocolIdentifier,
-- 	nonStandardData			NonStandardParameter OPTIONAL,
-- 	gatekeeperIdentifier	GatekeeperIdentifier OPTIONAL,
-- 	rasAddress				TransportAddress,
-- 	...,
-- 	alternateGatekeeper		SEQUENCE OF AlternateGK OPTIONAL,
-- 	authenticationMode		AuthenticationMechanism OPTIONAL,
-- 	tokens					SEQUENCE OF ClearToken OPTIONAL,
-- 	cryptoTokens			SEQUENCE OF CryptoH323Token OPTIONAL,
-- 	algorithmOID			OBJECT IDENTIFIER OPTIONAL,
-- 	integrity				SEQUENCE OF IntegrityMechanism OPTIONAL,
-- 	integrityCheckValue		ICV OPTIONAL
-- }
-- ------------------------------------------------------------- --

--<ASN1.PDU
--		H323-MESSAGES.GatekeeperConfirm>--
--<OSS.TYPENAME 
--		H323-MESSAGES.GatekeeperConfirm
--		"EmGCF">--
--<OSS.FIELDNAME 
--		H323-MESSAGES.GatekeeperConfirm.requestSeqNum
--		"requestSeqNum">--
--<OSS.FIELDNAME 
--		H323-MESSAGES.GatekeeperConfirm.protocolIdentifier
--		"protocolIdentifier">--
--<OSS.FIELDNAME 
--		H323-MESSAGES.GatekeeperConfirm.nonStandardData
--		"nonStandardData">--
--<OSS.DefineName
--		H323-MESSAGES.GatekeeperConfirm.nonStandardData
--		"EM_GCF_nonStandardData">--
--<OSS.FIELDNAME 
--		H323-MESSAGES.GatekeeperConfirm.gatekeeperIdentifier
--		"gatekeeperIdentifier">--
--<OSS.DefineName
--		H323-MESSAGES.GatekeeperConfirm.gatekeeperIdentifier
--		"EM_GCF_gatekeeperIdentifier">--
--<OSS.FIELDNAME 
--		H323-MESSAGES.GatekeeperConfirm.rasAddress
--		"rasAddress">--
--<OSS.FIELDNAME 
--		H323-MESSAGES.GatekeeperConfirm.alternateGatekeeper
--		"alternateGatekeeper">--
--<OSS.DefineName
--		H323-MESSAGES.GatekeeperConfirm.alternateGatekeeper
--		"EM_GCF_alternateGatekeeper">--
--<OSS.FIELDNAME 
--		H323-MESSAGES.GatekeeperConfirm.authenticationMode
--		"authenticationMode">--
--<OSS.DefineName
--		H323-MESSAGES.GatekeeperConfirm.authenticationMode
--		"EM_authenticationMode">--
--<OSS.FIELDNAME 
--		H323-MESSAGES.GatekeeperConfirm.tokens
--		"tokens">--
--<OSS.DefineName
--		H323-MESSAGES.GatekeeperConfirm.tokens
--		"EM_GCF_tokens">--
--<OSS.FIELDNAME 
--		H323-MESSAGES.GatekeeperConfirm.cryptoTokens
--		"cryptoTokens">--
--<OSS.DefineName
--		H323-MESSAGES.GatekeeperConfirm.cryptoTokens
--		"EM_GCF_cryptoTokens">--
--<OSS.FIELDNAME 
--		H323-MESSAGES.GatekeeperConfirm.algorithmOID
--		"algorithmOID">--
--<OSS.DefineName
--		H323-MESSAGES.GatekeeperConfirm.algorithmOID
--		"EM_algorithmOID">--
--<OSS.FIELDNAME 
--		H323-MESSAGES.GatekeeperConfirm.integrity
--		"integrity">--
--<OSS.DefineName
--		H323-MESSAGES.GatekeeperConfirm.integrity
--		"EM_GCF_integrity">--
--<OSS.FIELDNAME 
--		H323-MESSAGES.GatekeeperConfirm.integrityCheckValue
--		"integrityCheckValue">--
--<OSS.DefineName
--		H323-MESSAGES.GatekeeperConfirm.integrityCheckValue
--		"EM_GCF_integrityCheckValue">--

-- ------------------------------------------------------------- --
-- GatekeeperReject ::= SEQUENCE
-- {
-- 	requestSeqNum			RequestSeqNum,
-- 	protocolIdentifier		ProtocolIdentifier,
-- 	nonStandardData			NonStandardParameter OPTIONAL,
-- 	gatekeeperIdentifier	GatekeeperIdentifier OPTIONAL,
-- 	rejectReason			GatekeeperRejectReason,
-- 	...,
-- 	altGKInfo				AltGKInfo OPTIONAL,
-- 	tokens					SEQUENCE OF ClearToken OPTIONAL,
-- 	cryptoTokens			SEQUENCE OF CryptoH323Token OPTIONAL,
-- 	integrityCheckValue		ICV OPTIONAL
-- }
-- ------------------------------------------------------------- --

--<ASN1.PDU
--		H323-MESSAGES.GatekeeperReject>--
--<OSS.TYPENAME 
--		H323-MESSAGES.GatekeeperReject
--		"EmGRJ">--
--<OSS.FIELDNAME 
--		H323-MESSAGES.GatekeeperReject.requestSeqNum
--		"requestSeqNum">--
--<OSS.FIELDNAME 
--		H323-MESSAGES.GatekeeperReject.protocolIdentifier
--		"protocolIdentifier">--
--<OSS.FIELDNAME 
--		H323-MESSAGES.GatekeeperReject.nonStandardData
--		"nonStandardData">--
--<OSS.DefineName
--		H323-MESSAGES.GatekeeperReject.nonStandardData
--		"EM_GRJ_nonStandardData">--
--<OSS.FIELDNAME 
--		H323-MESSAGES.GatekeeperReject.gatekeeperIdentifier
--		"gatekeeperIdentifier">--
--<OSS.DefineName
--		H323-MESSAGES.GatekeeperReject.gatekeeperIdentifier
--		"EM_GRJ_gatekeeperIdentifier">--
--<OSS.FIELDNAME 
--		H323-MESSAGES.GatekeeperReject.rejectReason
--		"rejectReason">--
--<OSS.FIELDNAME 
--		H323-MESSAGES.GatekeeperReject.altGKInfo
--		"altGKInfo">--
--<OSS.DefineName
--		H323-MESSAGES.GatekeeperReject.altGKInfo
--		"EM_GRJ_altGKInfo">--
--<OSS.FIELDNAME 
--		H323-MESSAGES.GatekeeperReject.tokens
--		"tokens">--
--<OSS.DefineName
--		H323-MESSAGES.GatekeeperReject.tokens
--		"EM_GRJ_tokens">--
--<OSS.FIELDNAME 
--		H323-MESSAGES.GatekeeperReject.cryptoTokens
--		"cryptoTokens">--
--<OSS.DefineName
--		H323-MESSAGES.GatekeeperReject.cryptoTokens
--		"EM_GRJ_cryptoTokens">--
--<OSS.FIELDNAME 
--		H323-MESSAGES.GatekeeperReject.integrityCheckValue
--		"integrityCheckValue">--
--<OSS.DefineName
--		H323-MESSAGES.GatekeeperReject.integrityCheckValue
--		"EM_GRJ_integrityCheckValue">--

-- ------------------------------------------------------------- --
-- GatekeeperRejectReason ::= CHOICE
-- {
-- 	resourceUnavailable		NULL,
-- 	terminalExcluded		NULL,
-- 	invalidRevision			NULL,
-- 	undefinedReason			NULL,
-- 	...,
-- 	securityDenial			NULL
-- }
-- ------------------------------------------------------------- --

--<ASN1.PDU
--		H323-MESSAGES.GatekeeperRejectReason>--
--<OSS.TYPENAME 
--		H323-MESSAGES.GatekeeperRejectReason
--		"EmGRJReason">--
--<OSS.FIELDNAME 
--		H323-MESSAGES.GatekeeperRejectReason.resourceUnavailable
--		"resourceUnavailable">--
--<OSS.DefineName
--		H323-MESSAGES.GatekeeperRejectReason.resourceUnavailable
--		"EM_GRJ_resourceUnavailable">--
--<OSS.FIELDNAME 
--		H323-MESSAGES.GatekeeperRejectReason.terminalExcluded
--		"terminalExcluded">--
--<OSS.DefineName
--		H323-MESSAGES.GatekeeperRejectReason.terminalExcluded
--		"EM_terminalExcluded">--
--<OSS.FIELDNAME 
--		H323-MESSAGES.GatekeeperRejectReason.invalidRevision
--		"invalidRevision">--
--<OSS.DefineName
--		H323-MESSAGES.GatekeeperRejectReason.invalidRevision
--		"EM_GRJ_invalidRevision">--
--<OSS.FIELDNAME 
--		H323-MESSAGES.GatekeeperRejectReason.undefinedReason
--		"undefinedReason">--
--<OSS.DefineName
--		H323-MESSAGES.GatekeeperRejectReason.undefinedReason
--		"EM_GRJ_undefinedReason">--
--<OSS.FIELDNAME 
--		H323-MESSAGES.GatekeeperRejectReason.securityDenial
--		"securityDenial">--
--<OSS.DefineName
--		H323-MESSAGES.GatekeeperRejectReason.securityDenial
--		"EM_GRJ_securityDenial">--

-- ------------------------------------------------------------- --
-- RegistrationRequest ::= SEQUENCE
-- {
-- 	requestSeqNum			RequestSeqNum,
-- 	protocolIdentifier		ProtocolIdentifier,
-- 	nonStandardData			NonStandardParameter OPTIONAL,
-- 	discoveryComplete		BOOLEAN,
-- 	callSignalAddress		SEQUENCE OF TransportAddress,
-- 	rasAddress				SEQUENCE OF TransportAddress,
-- 	terminalType			EndpointType,
-- 	terminalAlias			SEQUENCE OF AliasAddress OPTIONAL,
-- 	gatekeeperIdentifier	GatekeeperIdentifier OPTIONAL,
-- 	endpointVendor			VendorIdentifier,
-- 	...,
-- 	alternateEndpoints		SEQUENCE OF Endpoint OPTIONAL,
-- 	timeToLive				TimeToLive OPTIONAL,
-- 	tokens					SEQUENCE OF ClearToken OPTIONAL,
-- 	cryptoTokens			SEQUENCE OF CryptoH323Token OPTIONAL,
-- 	integrityCheckValue		ICV OPTIONAL,
-- 	keepAlive				BOOLEAN,
-- 	endpointIdentifier		EndpointIdentifier OPTIONAL,
-- 	willSupplyUUIEs			BOOLEAN
-- }
-- ------------------------------------------------------------- --

--<ASN1.PDU
--		H323-MESSAGES.RegistrationRequest>--
--<OSS.TYPENAME 
--		H323-MESSAGES.RegistrationRequest
--		"EmRRQ">--
--<OSS.FIELDNAME 
--		H323-MESSAGES.RegistrationRequest.requestSeqNum
--		"requestSeqNum">--
--<OSS.FIELDNAME 
--		H323-MESSAGES.RegistrationRequest.protocolIdentifier
--		"protocolIdentifier">--
--<OSS.FIELDNAME 
--		H323-MESSAGES.RegistrationRequest.nonStandardData
--		"nonStandardData">--
--<OSS.DefineName
--		H323-MESSAGES.RegistrationRequest.nonStandardData
--		"EM_RRQ_nonStandardData">--
--<OSS.FIELDNAME 
--		H323-MESSAGES.RegistrationRequest.discoveryComplete
--		"discoveryComplete">--
--<OSS.FIELDNAME 
--		H323-MESSAGES.RegistrationRequest.callSignalAddress
--		"callSignalAddress">--
--<OSS.FIELDNAME 
--		H323-MESSAGES.RegistrationRequest.rasAddress
--		"rasAddress">--
--<OSS.FIELDNAME 
--		H323-MESSAGES.RegistrationRequest.terminalType
--		"terminalType">--
--<OSS.FIELDNAME 
--		H323-MESSAGES.RegistrationRequest.terminalAlias
--		"terminalAlias">--
--<OSS.DefineName
--		H323-MESSAGES.RegistrationRequest.terminalAlias
--		"EM_RRQ_terminalAlias">--
--<OSS.FIELDNAME 
--		H323-MESSAGES.RegistrationRequest.gatekeeperIdentifier
--		"gatekeeperIdentifier">--
--<OSS.DefineName
--		H323-MESSAGES.RegistrationRequest.gatekeeperIdentifier
--		"EM_RRQ_gatekeeperIdentifier">--
--<OSS.FIELDNAME 
--		H323-MESSAGES.RegistrationRequest.endpointVendor
--		"endpointVendor">--
--<OSS.FIELDNAME 
--		H323-MESSAGES.RegistrationRequest.alternateEndpoints
--		"alternateEndpoints">--
--<OSS.DefineName
--		H323-MESSAGES.RegistrationRequest.alternateEndpoints
--		"EM_RRQ_alternateEndpoints">--
--<OSS.FIELDNAME 
--		H323-MESSAGES.RegistrationRequest.timeToLive
--		"timeToLive">--
--<OSS.DefineName
--		H323-MESSAGES.RegistrationRequest.timeToLive
--		"EM_RRQ_timeToLive">--
--<OSS.FIELDNAME 
--		H323-MESSAGES.RegistrationRequest.tokens
--		"tokens">--
--<OSS.DefineName
--		H323-MESSAGES.RegistrationRequest.tokens
--		"EM_RRQ_tokens">--
--<OSS.FIELDNAME 
--		H323-MESSAGES.RegistrationRequest.cryptoTokens
--		"cryptoTokens">--
--<OSS.DefineName
--		H323-MESSAGES.RegistrationRequest.cryptoTokens
--		"EM_RRQ_cryptoTokens">--
--<OSS.FIELDNAME 
--		H323-MESSAGES.RegistrationRequest.integrityCheckValue
--		"integrityCheckValue">--
--<OSS.DefineName
--		H323-MESSAGES.RegistrationRequest.integrityCheckValue
--		"EM_RRQ_integrityCheckValue">--
--<OSS.FIELDNAME 
--		H323-MESSAGES.RegistrationRequest.keepAlive
--		"keepAlive">--
--<OSS.DefineName
--		H323-MESSAGES.RegistrationRequest.keepAlive
--		"EM_keepAlive">--
--<OSS.FIELDNAME 
--		H323-MESSAGES.RegistrationRequest.endpointIdentifier
--		"endpointIdentifier">--
--<OSS.DefineName
--		H323-MESSAGES.RegistrationRequest.endpointIdentifier
--		"EM_RRQ_endpointIdentifier">--
--<OSS.FIELDNAME 
--		H323-MESSAGES.RegistrationRequest.willSupplyUUIEs
--		"willSupplyUUIEs">--
--<OSS.DefineName
--		H323-MESSAGES.RegistrationRequest.willSupplyUUIEs
--		"EM_RRQ_willSupplyUUIEs">--

-- ------------------------------------------------------------- --
-- RegistrationConfirm ::= SEQUENCE
-- {
-- 	requestSeqNum			RequestSeqNum,
-- 	protocolIdentifier		ProtocolIdentifier,
-- 	nonStandardData			NonStandardParameter OPTIONAL,
-- 	callSignalAddress		SEQUENCE OF TransportAddress,
-- 	terminalAlias			SEQUENCE OF AliasAddress OPTIONAL,
-- 	gatekeeperIdentifier	GatekeeperIdentifier OPTIONAL,
-- 	endpointIdentifier		EndpointIdentifier,
-- 	...,	
-- 	alternateGatekeeper		SEQUENCE OF AlternateGK OPTIONAL,
-- 	timeToLive				TimeToLive OPTIONAL,
-- 	tokens					SEQUENCE OF ClearToken OPTIONAL,
-- 	cryptoTokens			SEQUENCE OF CryptoH323Token OPTIONAL,
-- 	integrityCheckValue		ICV OPTIONAL,
-- 	willRespondToIRR		BOOLEAN,
-- 	preGrantedARQ			SEQUENCE
-- 	{
-- 		makeCall							BOOLEAN,
-- 		useGKCallSignalAddressToMakeCall	BOOLEAN,
-- 		answerCall							BOOLEAN,
-- 		useGKCallSignalAddressToAnswer		BOOLEAN,
-- 		...
-- 	} OPTIONAL
-- }
-- ------------------------------------------------------------- --

--<ASN1.PDU
--		H323-MESSAGES.RegistrationConfirm>--
--<OSS.TYPENAME 
--		H323-MESSAGES.RegistrationConfirm
--		"EmRCF">--
--<OSS.FIELDNAME 
--		H323-MESSAGES.RegistrationConfirm.requestSeqNum
--		"requestSeqNum">--
--<OSS.FIELDNAME 
--		H323-MESSAGES.RegistrationConfirm.protocolIdentifier
--		"protocolIdentifier">--
--<OSS.FIELDNAME 
--		H323-MESSAGES.RegistrationConfirm.nonStandardData
--		"nonStandardData">--
--<OSS.DefineName
--		H323-MESSAGES.RegistrationConfirm.nonStandardData
--		"EM_RCF_nonStandardData">--
--<OSS.FIELDNAME 
--		H323-MESSAGES.RegistrationConfirm.callSignalAddress
--		"callSignalAddress">--
--<OSS.FIELDNAME 
--		H323-MESSAGES.RegistrationConfirm.terminalAlias
--		"terminalAlias">--
--<OSS.DefineName
--		H323-MESSAGES.RegistrationConfirm.terminalAlias
--		"EM_RCF_terminalAlias">--
--<OSS.FIELDNAME 
--		H323-MESSAGES.RegistrationConfirm.gatekeeperIdentifier
--		"gatekeeperIdentifier">--
--<OSS.DefineName
--		H323-MESSAGES.RegistrationConfirm.gatekeeperIdentifier
--		"EM_RCF_gatekeeperIdentifier">--
--<OSS.FIELDNAME 
--		H323-MESSAGES.RegistrationConfirm.endpointIdentifier
--		"endpointIdentifier">--
--<OSS.FIELDNAME 
--		H323-MESSAGES.RegistrationConfirm.alternateGatekeeper
--		"alternateGatekeeper">--
--<OSS.DefineName
--		H323-MESSAGES.RegistrationConfirm.alternateGatekeeper
--		"EM_RCF_alternateGatekeeper">--
--<OSS.FIELDNAME 
--		H323-MESSAGES.RegistrationConfirm.timeToLive
--		"timeToLive">--
--<OSS.DefineName
--		H323-MESSAGES.RegistrationConfirm.timeToLive
--		"EM_RCF_timeToLive">--
--<OSS.FIELDNAME 
--		H323-MESSAGES.RegistrationConfirm.tokens
--		"tokens">--
--<OSS.DefineName
--		H323-MESSAGES.RegistrationConfirm.tokens
--		"EM_RCF_tokens">--
--<OSS.FIELDNAME 
--		H323-MESSAGES.RegistrationConfirm.cryptoTokens
--		"cryptoTokens">--
--<OSS.DefineName
--		H323-MESSAGES.RegistrationConfirm.cryptoTokens
--		"EM_RCF_cryptoTokens">--
--<OSS.FIELDNAME 
--		H323-MESSAGES.RegistrationConfirm.integrityCheckValue
--		"integrityCheckValue">--
--<OSS.DefineName
--		H323-MESSAGES.RegistrationConfirm.integrityCheckValue
--		"EM_RCF_integrityCheckValue">--
--<OSS.FIELDNAME 
--		H323-MESSAGES.RegistrationConfirm.willRespondToIRR
--		"willRespondToIRR">--
--<OSS.DefineName
--		H323-MESSAGES.RegistrationConfirm.willRespondToIRR
--		"EM_RCF_willRespondToIRR">--
--<OSS.TYPENAME
--		H323-MESSAGES.RegistrationConfirm.preGrantedARQ
--		"EmPreGrantedARQ">--
--<OSS.FIELDNAME 
--		H323-MESSAGES.RegistrationConfirm.preGrantedARQ
--		"preGrantedARQ">--
--<OSS.DefineName
--		H323-MESSAGES.RegistrationConfirm.preGrantedARQ
--		"EM_preGrantedARQ">--
--<OSS.FIELDNAME 
--		H323-MESSAGES.RegistrationConfirm.preGrantedARQ.makeCall
--		"makeCall">--
--<OSS.FIELDNAME 
--		H323-MESSAGES.RegistrationConfirm.preGrantedARQ.useGKCallSignalAddressToMakeCall
--		"useGKCallSignalAddressToMakeCall">--
--<OSS.FIELDNAME 
--		H323-MESSAGES.RegistrationConfirm.preGrantedARQ.answerCall
--		"answerCall">--
--<OSS.FIELDNAME 
--		H323-MESSAGES.RegistrationConfirm.preGrantedARQ.useGKCallSignalAddressToAnswer
--		"useGKCallSignalAddressToAnswer">--

-- ------------------------------------------------------------- --
-- RegistrationReject ::= SEQUENCE 
-- {
-- 	requestSeqNum			RequestSeqNum,
-- 	protocolIdentifier		ProtocolIdentifier,
-- 	nonStandardData			NonStandardParameter OPTIONAL,
-- 	rejectReason			RegistrationRejectReason,
-- 	gatekeeperIdentifier	GatekeeperIdentifier OPTIONAL,
-- 	...,
-- 	altGKInfo				AltGKInfo OPTIONAL,
-- 	tokens					SEQUENCE OF ClearToken OPTIONAL,
-- 	cryptoTokens			SEQUENCE OF CryptoH323Token OPTIONAL,
-- 	integrityCheckValue		ICV OPTIONAL
-- }
-- ------------------------------------------------------------- --

--<ASN1.PDU
--		H323-MESSAGES.RegistrationReject>--
--<OSS.TYPENAME 
--		H323-MESSAGES.RegistrationReject
--		"EmRRJ">--
--<OSS.FIELDNAME 
--		H323-MESSAGES.RegistrationReject.requestSeqNum
--		"requestSeqNum">--
--<OSS.FIELDNAME 
--		H323-MESSAGES.RegistrationReject.protocolIdentifier
--		"protocolIdentifier">--
--<OSS.FIELDNAME 
--		H323-MESSAGES.RegistrationReject.nonStandardData
--		"nonStandardData">--
--<OSS.DefineName
--		H323-MESSAGES.RegistrationReject.nonStandardData
--		"EM_RRJ_nonStandardData">--
--<OSS.FIELDNAME 
--		H323-MESSAGES.RegistrationReject.rejectReason
--		"rejectReason">--
--<OSS.FIELDNAME 
--		H323-MESSAGES.RegistrationReject.gatekeeperIdentifier
--		"gatekeeperIdentifier">--
--<OSS.DefineName
--		H323-MESSAGES.RegistrationReject.gatekeeperIdentifier
--		"EM_RRJ_gatekeeperIdentifier">--
--<OSS.FIELDNAME 
--		H323-MESSAGES.RegistrationReject.altGKInfo
--		"altGKInfo">--
--<OSS.DefineName
--		H323-MESSAGES.RegistrationReject.altGKInfo
--		"EM_RRJ_altGKInfo">--
--<OSS.FIELDNAME 
--		H323-MESSAGES.RegistrationReject.tokens
--		"tokens">--
--<OSS.DefineName
--		H323-MESSAGES.RegistrationReject.tokens
--		"EM_RRJ_tokens">--
--<OSS.FIELDNAME 
--		H323-MESSAGES.RegistrationReject.cryptoTokens
--		"cryptoTokens">--
--<OSS.DefineName
--		H323-MESSAGES.RegistrationReject.cryptoTokens
--		"EM_RRJ_cryptoTokens">--
--<OSS.FIELDNAME 
--		H323-MESSAGES.RegistrationReject.integrityCheckValue
--		"integrityCheckValue">--
--<OSS.DefineName
--		H323-MESSAGES.RegistrationReject.integrityCheckValue
--		"EM_RRJ_integrityCheckValue">--

-- ------------------------------------------------------------- --
-- RegistrationRejectReason ::= CHOICE
-- {
-- 	discoveryRequired			NULL,
-- 	invalidRevision				NULL,
-- 	invalidCallSignalAddress	NULL,
-- 	invalidRASAddress			NULL,
-- 	duplicateAlias				SEQUENCE OF AliasAddress,
-- 	invalidTerminalType			NULL,
-- 	undefinedReason				NULL,
-- 	transportNotSupported		NULL,
-- 	...,
-- 	transportQOSNotSupported	NULL,
-- 	resourceUnavailable			NULL,
-- 	invalidAlias				NULL,
-- 	securityDenial				NULL
-- }
-- ------------------------------------------------------------- --

--<ASN1.PDU
--		H323-MESSAGES.RegistrationRejectReason>--
--<OSS.TYPENAME 
--		H323-MESSAGES.RegistrationRejectReason 
--		"EmRRJReason">--
--<OSS.FIELDNAME 
--		H323-MESSAGES.RegistrationRejectReason.discoveryRequired
--		"discoveryRequired">--
--<OSS.DefineName
--		H323-MESSAGES.RegistrationRejectReason.discoveryRequired
--		"EM_discoveryRequired">--
--<OSS.FIELDNAME 
--		H323-MESSAGES.RegistrationRejectReason.invalidRevision
--		"invalidRevision">--
--<OSS.DefineName
--		H323-MESSAGES.RegistrationRejectReason.invalidRevision
--		"EM_RRJ_invalidRevision">--
--<OSS.FIELDNAME 
--		H323-MESSAGES.RegistrationRejectReason.invalidCallSignalAddress
--		"invalidCallSignalAddress">--
--<OSS.DefineName
--		H323-MESSAGES.RegistrationRejectReason.invalidCallSignalAddress
--		"EM_invalidCallSignalAddress">--
--<OSS.FIELDNAME 
--		H323-MESSAGES.RegistrationRejectReason.invalidRASAddress
--		"invalidRASAddress">--
--<OSS.DefineName
--		H323-MESSAGES.RegistrationRejectReason.invalidRASAddress
--		"EM_invalidRASAddress">--
--<OSS.FIELDNAME 
--		H323-MESSAGES.RegistrationRejectReason.duplicateAlias
--		"duplicateAlias">--
--<OSS.DefineName
--		H323-MESSAGES.RegistrationRejectReason.duplicateAlias
--		"EM_duplicateAlias">--
--<OSS.FIELDNAME 
--		H323-MESSAGES.RegistrationRejectReason.invalidTerminalType
--		"invalidTerminalType">--
--<OSS.DefineName
--		H323-MESSAGES.RegistrationRejectReason.invalidTerminalType
--		"EM_invalidTerminalType">--
--<OSS.FIELDNAME 
--		H323-MESSAGES.RegistrationRejectReason.undefinedReason
--		"undefinedReason">--
--<OSS.DefineName
--		H323-MESSAGES.RegistrationRejectReason.undefinedReason
--		"EM_RRJ_undefinedReason">--
--<OSS.FIELDNAME 
--		H323-MESSAGES.RegistrationRejectReason.transportNotSupported
--		"transportNotSupported">--
--<OSS.DefineName
--		H323-MESSAGES.RegistrationRejectReason.transportNotSupported
--		"EM_transportNotSupported">--
--<OSS.FIELDNAME 
--		H323-MESSAGES.RegistrationRejectReason.transportQOSNotSupported
--		"transportQOSNotSupported">--
--<OSS.DefineName
--		H323-MESSAGES.RegistrationRejectReason.transportQOSNotSupported
--		"EM_transportQOSNotSupported">--
--<OSS.FIELDNAME 
--		H323-MESSAGES.RegistrationRejectReason.resourceUnavailable
--		"resourceUnavailable">--
--<OSS.DefineName
--		H323-MESSAGES.RegistrationRejectReason.resourceUnavailable
--		"EM_RRJ_resourceUnavailable">--
--<OSS.FIELDNAME 
--		H323-MESSAGES.RegistrationRejectReason.invalidAlias
--		"invalidAlias">--
--<OSS.DefineName
--		H323-MESSAGES.RegistrationRejectReason.invalidAlias
--		"EM_invalidAlias">--
--<OSS.FIELDNAME 
--		H323-MESSAGES.RegistrationRejectReason.securityDenial
--		"securityDenial">--
--<OSS.DefineName
--		H323-MESSAGES.RegistrationRejectReason.securityDenial
--		"EM_RRJ_securityDenial">--

-- ------------------------------------------------------------- --
-- UnregistrationRequest ::= SEQUENCE
-- {
-- 	requestSeqNum			RequestSeqNum,
-- 	callSignalAddress		SEQUENCE OF TransportAddress,
-- 	endpointAlias			SEQUENCE OF AliasAddress OPTIONAL,
-- 	nonStandardData			NonStandardParameter OPTIONAL,
-- 	endpointIdentifier		EndpointIdentifier OPTIONAL,
-- 	...,
-- 	alternateEndpoints		SEQUENCE OF Endpoint OPTIONAL,
-- 	gatekeeperIdentifier	GatekeeperIdentifier OPTIONAL,
-- 	tokens					SEQUENCE OF ClearToken OPTIONAL,
-- 	cryptoTokens			SEQUENCE OF CryptoH323Token OPTIONAL,
-- 	integrityCheckValue		ICV OPTIONAL,
-- 	reason					UnregRequestReason OPTIONAL
-- }
-- ------------------------------------------------------------- --

--<ASN1.PDU
--		H323-MESSAGES.UnregistrationRequest>--
--<OSS.TYPENAME 
--		H323-MESSAGES.UnregistrationRequest
--		"EmURQ">--
--<OSS.FIELDNAME 
--		H323-MESSAGES.UnregistrationRequest.requestSeqNum
--		"requestSeqNum">--
--<OSS.FIELDNAME 
--		H323-MESSAGES.UnregistrationRequest.callSignalAddress
--		"callSignalAddress">--
--<OSS.FIELDNAME 
--		H323-MESSAGES.UnregistrationRequest.endpointAlias
--		"endpointAlias">--
--<OSS.DefineName
--		H323-MESSAGES.UnregistrationRequest.endpointAlias
--		"EM_URQ_endpointAlias">--
--<OSS.FIELDNAME 
--		H323-MESSAGES.UnregistrationRequest.nonStandardData
--		"nonStandardData">--
--<OSS.DefineName
--		H323-MESSAGES.UnregistrationRequest.nonStandardData
--		"EM_URQ_nonStandardData">--
--<OSS.FIELDNAME 
--		H323-MESSAGES.UnregistrationRequest.endpointIdentifier
--		"endpointIdentifier">--
--<OSS.DefineName
--		H323-MESSAGES.UnregistrationRequest.endpointIdentifier
--		"EM_URQ_endpointIdentifier">--
--<OSS.FIELDNAME 
--		H323-MESSAGES.UnregistrationRequest.alternateEndpoints
--		"alternateEndpoints">--
--<OSS.DefineName
--		H323-MESSAGES.UnregistrationRequest.alternateEndpoints
--		"EM_URQ_alternateEndpoints">--
--<OSS.FIELDNAME 
--		H323-MESSAGES.UnregistrationRequest.gatekeeperIdentifier
--		"gatekeeperIdentifier">--
--<OSS.DefineName
--		H323-MESSAGES.UnregistrationRequest.gatekeeperIdentifier
--		"EM_URQ_gatekeeperIdentifier">--
--<OSS.FIELDNAME 
--		H323-MESSAGES.UnregistrationRequest.tokens
--		"tokens">--
--<OSS.DefineName
--		H323-MESSAGES.UnregistrationRequest.tokens
--		"EM_URQ_tokens">--
--<OSS.FIELDNAME 
--		H323-MESSAGES.UnregistrationRequest.cryptoTokens
--		"cryptoTokens">--
--<OSS.DefineName
--		H323-MESSAGES.UnregistrationRequest.cryptoTokens
--		"EM_URQ_cryptoTokens">--
--<OSS.FIELDNAME 
--		H323-MESSAGES.UnregistrationRequest.integrityCheckValue
--		"integrityCheckValue">--
--<OSS.DefineName
--		H323-MESSAGES.UnregistrationRequest.integrityCheckValue
--		"EM_URQ_integrityCheckValue">--
--<OSS.FIELDNAME 
--		H323-MESSAGES.UnregistrationRequest.reason
--		"reason">--
--<OSS.DefineName
--		H323-MESSAGES.UnregistrationRequest.reason
--		"EM_URQ_reason">--

-- ------------------------------------------------------------- --
-- UnregRequestReason ::= CHOICE
-- {
-- 	reregistrationRequired		NULL,
-- 	ttlExpired					NULL,
-- 	securityDenial				NULL,
-- 	undefinedReason				NULL,
-- 	...
-- }
-- ------------------------------------------------------------- --

--<ASN1.PDU
--		H323-MESSAGES.UnregRequestReason>--
--<OSS.TYPENAME 
--		H323-MESSAGES.UnregRequestReason
--		"EmURQReason">--
--<OSS.FIELDNAME 
--		H323-MESSAGES.UnregRequestReason.reregistrationRequired
--		"reregistrationRequired">--
--<OSS.DefineName
--		H323-MESSAGES.UnregRequestReason.reregistrationRequired
--		"EM_reregistrationRequired">--
--<OSS.FIELDNAME 
--		H323-MESSAGES.UnregRequestReason.ttlExpired
--		"ttlExpired">--
--<OSS.DefineName
--		H323-MESSAGES.UnregRequestReason.ttlExpired
--		"EM_ttlExpired">--
--<OSS.FIELDNAME 
--		H323-MESSAGES.UnregRequestReason.securityDenial
--		"securityDenial">--
--<OSS.DefineName
--		H323-MESSAGES.UnregRequestReason.securityDenial
--		"EM_URQ_securityDenial">--
--<OSS.FIELDNAME 
--		H323-MESSAGES.UnregRequestReason.undefinedReason
--		"undefinedReason">--
--<OSS.DefineName
--		H323-MESSAGES.UnregRequestReason.undefinedReason
--		"EM_URQ_undefinedReason">--

-- ------------------------------------------------------------- --
-- UnregistrationConfirm ::= SEQUENCE
-- {
-- 	requestSeqNum		RequestSeqNum,
-- 	nonStandardData		NonStandardParameter OPTIONAL,
-- 	...,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.UnregistrationConfirm>--
--<OSS.TYPENAME 
--		H323-MESSAGES.UnregistrationConfirm
--		"EmUCF">--
--<OSS.FIELDNAME 
--		H323-MESSAGES.UnregistrationConfirm.requestSeqNum
--		"requestSeqNum">--
--<OSS.FIELDNAME 
--		H323-MESSAGES.UnregistrationConfirm.nonStandardData
--		"nonStandardData">--
--<OSS.DefineName
--		H323-MESSAGES.UnregistrationConfirm.nonStandardData
--		"EM_UCF_nonStandardData">--
--<OSS.FIELDNAME 
--		H323-MESSAGES.UnregistrationConfirm.tokens
--		"tokens">--
--<OSS.DefineName
--		H323-MESSAGES.UnregistrationConfirm.tokens
--		"EM_UCF_tokens">--
--<OSS.FIELDNAME 
--		H323-MESSAGES.UnregistrationConfirm.cryptoTokens
--		"cryptoTokens">--
--<OSS.DefineName
--		H323-MESSAGES.UnregistrationConfirm.cryptoTokens
--		"EM_UCF_cryptoTokens">--
--<OSS.FIELDNAME 
--		H323-MESSAGES.UnregistrationConfirm.integrityCheckValue
--		"integrityCheckValue">--
--<OSS.DefineName
--		H323-MESSAGES.UnregistrationConfirm.integrityCheckValue
--		"EM_UCF_integrityCheckValue">--

-- ------------------------------------------------------------- --
-- UnregistrationReject ::= SEQUENCE
-- {
-- 	requestSeqNum		RequestSeqNum,
-- 	rejectReason		UnregRejectReason,
-- 	nonStandardData		NonStandardParameter OPTIONAL,
-- 	...,
-- 	altGKInfo			AltGKInfo OPTIONAL,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.UnregistrationReject>--
--<OSS.TYPENAME 
--		H323-MESSAGES.UnregistrationReject
--		"EmURJ">--
--<OSS.FIELDNAME 
--		H323-MESSAGES.UnregistrationReject.requestSeqNum
--		"requestSeqNum">--
--<OSS.FIELDNAME 
--		H323-MESSAGES.UnregistrationReject.rejectReason
--		"rejectReason">--
--<OSS.FIELDNAME 
--		H323-MESSAGES.UnregistrationReject.nonStandardData
--		"nonStandardData">--
--<OSS.DefineName
--		H323-MESSAGES.UnregistrationReject.nonStandardData
--		"EM_URJ_nonStandardData">--
--<OSS.FIELDNAME 
--		H323-MESSAGES.UnregistrationReject.altGKInfo
--		"altGKInfo">--
--<OSS.DefineName
--		H323-MESSAGES.UnregistrationReject.altGKInfo
--		"EM_URJ_altGKInfo">--
--<OSS.FIELDNAME 
--		H323-MESSAGES.UnregistrationReject.tokens
--		"tokens">--
--<OSS.DefineName
--		H323-MESSAGES.UnregistrationReject.tokens
--		"EM_URJ_tokens">--
--<OSS.FIELDNAME 
--		H323-MESSAGES.UnregistrationReject.cryptoTokens
--		"cryptoTokens">--
--<OSS.DefineName
--		H323-MESSAGES.UnregistrationReject.cryptoTokens
--		"EM_URJ_cryptoTokens">--
--<OSS.FIELDNAME 
--		H323-MESSAGES.UnregistrationReject.integrityCheckValue
--		"integrityCheckValue">--
--<OSS.DefineName
--		H323-MESSAGES.UnregistrationReject.integrityCheckValue
--		"EM_URJ_integrityCheckValue">--

-- ------------------------------------------------------------- --
-- UnregRejectReason ::= CHOICE
-- {
-- 	notCurrentlyRegistered	NULL,
-- 	callInProgress			NULL,
-- 	undefinedReason			NULL,
-- 	...,
-- 	permissionDenied		NULL,
-- 	securityDenial			NULL
-- }
-- ------------------------------------------------------------- --

--<ASN1.PDU
--		H323-MESSAGES.UnregRejectReason>--
--<OSS.TYPENAME 
--		H323-MESSAGES.UnregRejectReason
--		"EmURJReason">--
--<OSS.FIELDNAME 
--		H323-MESSAGES.UnregRejectReason.notCurrentlyRegistered
--		"notCurrentlyRegistered">--
--<OSS.DefineName
--		H323-MESSAGES.UnregRejectReason.notCurrentlyRegistered
--		"EM_notCurrentlyRegistered">--
--<OSS.FIELDNAME 
--		H323-MESSAGES.UnregRejectReason.callInProgress
--		"callInProgress">--
--<OSS.DefineName
--		H323-MESSAGES.UnregRejectReason.callInProgress
--		"EM_callInProgress">--
--<OSS.FIELDNAME 
--		H323-MESSAGES.UnregRejectReason.undefinedReason
--		"undefinedReason">--
--<OSS.DefineName
--		H323-MESSAGES.UnregRejectReason.undefinedReason
--		"EM_URJ_undefinedReason">--
--<OSS.FIELDNAME 
--		H323-MESSAGES.UnregRejectReason.permissionDenied
--		"permissionDenied">--
--<OSS.DefineName
--		H323-MESSAGES.UnregRejectReason.permissionDenied
--		"EM_permissionDenied">--
--<OSS.FIELDNAME 
--		H323-MESSAGES.UnregRejectReason.securityDenial
--		"securityDenial">--
--<OSS.DefineName
--		H323-MESSAGES.UnregRejectReason.securityDenial
--		"EM_URJ_securityDenial">--

-- ------------------------------------------------------------- --
-- AdmissionRequest ::= SEQUENCE
-- {
-- 	requestSeqNum			RequestSeqNum,
-- 	callType				CallType,
-- 	callModel				CallModel OPTIONAL,
-- 	endpointIdentifier		EndpointIdentifier,
-- 	destinationInfo			SEQUENCE OF AliasAddress OPTIONAL,	
-- 	destCallSignalAddress	TransportAddress OPTIONAL,		
-- 	destExtraCallInfo		SEQUENCE OF AliasAddress OPTIONAL,
-- 	srcInfo					SEQUENCE OF AliasAddress,
-- 	srcCallSignalAddress	TransportAddress OPTIONAL, 
-- 	bandWidth				BandWidth,
-- 	callReferenceValue		CallReferenceValue,
-- 	nonStandardData			NonStandardParameter OPTIONAL,
-- 	callServices			QseriesOptions OPTIONAL,
-- 	conferenceID			ConferenceIdentifier,
-- 	activeMC				BOOLEAN,
-- 	answerCall				BOOLEAN,
-- 	...,
-- 	canMapAlias				BOOLEAN,
-- 	callIdentifier			CallIdentifier,
-- 	srcAlternatives			SEQUENCE OF Endpoint OPTIONAL,
-- 	destAlternatives		SEQUENCE OF Endpoint OPTIONAL,
-- 	gatekeeperIdentifier	GatekeeperIdentifier OPTIONAL,
-- 	tokens					SEQUENCE OF ClearToken OPTIONAL,
-- 	cryptoTokens			SEQUENCE OF CryptoH323Token OPTIONAL,
-- 	integrityCheckValue		ICV OPTIONAL,
-- 	transportQOS			TransportQOS OPTIONAL,
-- 	willSupplyUUIEs			BOOLEAN
-- }
-- ------------------------------------------------------------- --

--<ASN1.PDU
--		H323-MESSAGES.AdmissionRequest>--
--<OSS.TYPENAME 
--		H323-MESSAGES.AdmissionRequest
--		"EmARQ">--
--<OSS.FIELDNAME 
--		H323-MESSAGES.AdmissionRequest.requestSeqNum
--		"requestSeqNum">--
--<OSS.FIELDNAME 
--		H323-MESSAGES.AdmissionRequest.callType
--		"callType">--
--<OSS.FIELDNAME 
--		H323-MESSAGES.AdmissionRequest.callModel
--		"callModel">--
--<OSS.DefineName
--		H323-MESSAGES.AdmissionRequest.callModel
--		"EM_callModel">--
--<OSS.FIELDNAME 
--		H323-MESSAGES.AdmissionRequest.endpointIdentifier
--		"endpointIdentifier">--
--<OSS.FIELDNAME 
--		H323-MESSAGES.AdmissionRequest.destinationInfo
--		"destinationInfo">--
--<OSS.DefineName
--		H323-MESSAGES.AdmissionRequest.destinationInfo
--		"EM_ARQ_destinationInfo">--
--<OSS.FIELDNAME 
--		H323-MESSAGES.AdmissionRequest.destCallSignalAddress
--		"destCallSignalAddress">--
--<OSS.DefineName
--		H323-MESSAGES.AdmissionRequest.destCallSignalAddress
--		"EM_ARQ_destCallSignalAddress">--
--<OSS.FIELDNAME 
--		H323-MESSAGES.AdmissionRequest.destExtraCallInfo
--		"destExtraCallInfo">--
--<OSS.DefineName
--		H323-MESSAGES.AdmissionRequest.destExtraCallInfo
--		"EM_ARQ_destExtraCallInfo">--
--<OSS.FIELDNAME 
--		H323-MESSAGES.AdmissionRequest.srcInfo
--		"srcInfo">--
--<OSS.FIELDNAME 
--		H323-MESSAGES.AdmissionRequest.srcCallSignalAddress
--		"srcCallSignalAddress">--
--<OSS.DefineName
--		H323-MESSAGES.AdmissionRequest.srcCallSignalAddress
--		"EM_srcCallSignalAddress">--
--<OSS.FIELDNAME 
--		H323-MESSAGES.AdmissionRequest.bandWidth
--		"bandWidth">--
--<OSS.FIELDNAME 
--		H323-MESSAGES.AdmissionRequest.callReferenceValue
--		"callReferenceValue">--
--<OSS.FIELDNAME 
--		H323-MESSAGES.AdmissionRequest.nonStandardData
--		"nonStandardData">--
--<OSS.DefineName
--		H323-MESSAGES.AdmissionRequest.nonStandardData
--		"EM_ARQ_nonStandardData">--
--<OSS.FIELDNAME 
--		H323-MESSAGES.AdmissionRequest.callServices
--		"callServices">--
--<OSS.DefineName
--		H323-MESSAGES.AdmissionRequest.callServices
--		"EM_ARQ_callServices">--
--<OSS.FIELDNAME 
--		H323-MESSAGES.AdmissionRequest.conferenceID
--		"conferenceID">--
--<OSS.FIELDNAME 
--		H323-MESSAGES.AdmissionRequest.activeMC
--		"activeMC">--
--<OSS.FIELDNAME 
--		H323-MESSAGES.AdmissionRequest.answerCall
--		"answerCall">--
--<OSS.FIELDNAME 
--		H323-MESSAGES.AdmissionRequest.canMapAlias
--		"canMapAlias">--
--<OSS.DefineName
--		H323-MESSAGES.AdmissionRequest.canMapAlias
--		"EM_ARQ_canMapAlias">--
--<OSS.FIELDNAME 
--		H323-MESSAGES.AdmissionRequest.callIdentifier
--		"callIdentifier">--
--<OSS.DefineName
--		H323-MESSAGES.AdmissionRequest.callIdentifier
--		"EM_ARQ_callIdentifier">--
--<OSS.FIELDNAME 
--		H323-MESSAGES.AdmissionRequest.srcAlternatives
--		"srcAlternatives">--
--<OSS.DefineName
--		H323-MESSAGES.AdmissionRequest.srcAlternatives
--		"EM_srcAlternatives">--
--<OSS.FIELDNAME 
--		H323-MESSAGES.AdmissionRequest.destAlternatives
--		"destAlternatives">--
--<OSS.DefineName
--		H323-MESSAGES.AdmissionRequest.destAlternatives
--		"EM_destAlternatives">--
--<OSS.FIELDNAME 
--		H323-MESSAGES.AdmissionRequest.gatekeeperIdentifier
--		"gatekeeperIdentifier">--
--<OSS.DefineName
--		H323-MESSAGES.AdmissionRequest.gatekeeperIdentifier
--		"EM_ARQ_gatekeeperIdentifier">--
--<OSS.FIELDNAME 
--		H323-MESSAGES.AdmissionRequest.tokens
--		"tokens">--
--<OSS.DefineName
--		H323-MESSAGES.AdmissionRequest.tokens
--		"EM_ARQ_tokens">--
--<OSS.FIELDNAME 
--		H323-MESSAGES.AdmissionRequest.cryptoTokens
--		"cryptoTokens">--
--<OSS.DefineName
--		H323-MESSAGES.AdmissionRequest.cryptoTokens
--		"EM_ARQ_cryptoTokens">--
--<OSS.FIELDNAME 
--		H323-MESSAGES.AdmissionRequest.integrityCheckValue
--		"integrityCheckValue">--
--<OSS.DefineName
--		H323-MESSAGES.AdmissionRequest.integrityCheckValue
--		"EM_ARQ_integrityCheckValue">--
--<OSS.FIELDNAME 
--		H323-MESSAGES.AdmissionRequest.transportQOS
--		"transportQOS">--
--<OSS.DefineName
--		H323-MESSAGES.AdmissionRequest.transportQOS
--		"EM_ARQ_transportQOS">--
--<OSS.FIELDNAME 
--		H323-MESSAGES.AdmissionRequest.willSupplyUUIEs
--		"willSupplyUUIEs">--
--<OSS.DefineName
--		H323-MESSAGES.AdmissionRequest.willSupplyUUIEs
--		"EM_ARQ_willSupplyUUIEs">--

-- ------------------------------------------------------------- --
-- CallType ::= CHOICE
-- {
-- 	pointToPoint	NULL,
-- 	oneToN			NULL,
-- 	nToOne			NULL,
-- 	nToN			NULL,
-- 	...
-- }
-- ------------------------------------------------------------- --

--<ASN1.PDU
--		H323-MESSAGES.CallType>--
--<OSS.TYPENAME 
--		H323-MESSAGES.CallType
--		"EmCallType">--
--<OSS.FIELDNAME 
--		H323-MESSAGES.CallType.pointToPoint
--		"pointToPoint">--
--<OSS.DefineName
--		H323-MESSAGES.CallType.pointToPoint
--		"EM_pointToPoint">--
--<OSS.FIELDNAME 
--		H323-MESSAGES.CallType.oneToN
--		"oneToN">--
--<OSS.DefineName
--		H323-MESSAGES.CallType.oneToN
--		"EM_oneToN">--
--<OSS.FIELDNAME 
--		H323-MESSAGES.CallType.nToOne
--		"nToOne">--
--<OSS.DefineName
--		H323-MESSAGES.CallType.nToOne
--		"EM_nToOne">--
--<OSS.FIELDNAME 
--		H323-MESSAGES.CallType.nToN
--		"nToN">--
--<OSS.DefineName
--		H323-MESSAGES.CallType.nToN
--		"EM_nToN">--

-- ------------------------------------------------------------- --
-- CallModel ::= CHOICE
-- {
-- 	direct				NULL,
-- 	gatekeeperRouted	NULL,
-- 	...
-- }
-- ------------------------------------------------------------- --

--<ASN1.PDU
--		H323-MESSAGES.CallModel>--
--<OSS.TYPENAME 
--		H323-MESSAGES.CallModel
--		"EmCallModel">--
--<OSS.FIELDNAME 
--		H323-MESSAGES.CallModel.direct
--		"direct">--
--<OSS.DefineName
--		H323-MESSAGES.CallModel.direct
--		"EM_direct">--
--<OSS.FIELDNAME 
--		H323-MESSAGES.CallModel.gatekeeperRouted
--		"gatekeeperRouted">--
--<OSS.DefineName
--		H323-MESSAGES.CallModel.gatekeeperRouted
--		"EM_gatekeeperRouted">--

-- ------------------------------------------------------------- --
-- TransportQOS ::= CHOICE
-- {
-- 	endpointControlled		NULL,
-- 	gatekeeperControlled	NULL,
-- 	noControl				NULL,
-- 	...
-- }
-- ------------------------------------------------------------- --

--<ASN1.PDU
--		H323-MESSAGES.TransportQOS>--
--<OSS.TYPENAME 
--		H323-MESSAGES.TransportQOS
--		"EmTransportQOS">--
--<OSS.FIELDNAME 
--		H323-MESSAGES.TransportQOS.endpointControlled
--		"endpointControlled">--
--<OSS.DefineName
--		H323-MESSAGES.TransportQOS.endpointControlled
--		"EM_endpointControlled">--
--<OSS.FIELDNAME 
--		H323-MESSAGES.TransportQOS.gatekeeperControlled
--		"gatekeeperControlled">--
--<OSS.DefineName
--		H323-MESSAGES.TransportQOS.gatekeeperControlled
--		"EM_gatekeeperControlled">--
--<OSS.FIELDNAME 
--		H323-MESSAGES.TransportQOS.noControl
--		"noControl">--
--<OSS.DefineName
--		H323-MESSAGES.TransportQOS.noControl
--		"EM_noControl">--

-- ------------------------------------------------------------- --
-- AdmissionConfirm ::= SEQUENCE 
-- {
-- 	requestSeqNum			RequestSeqNum,
-- 	bandWidth				BandWidth,
-- 	callModel				CallModel,
-- 	destCallSignalAddress	TransportAddress,
-- 	irrFrequency			INTEGER (1..65535) OPTIONAL,
-- 	nonStandardData			NonStandardParameter OPTIONAL,
-- 	...,
-- 	destinationInfo			SEQUENCE OF AliasAddress OPTIONAL,
-- 	destExtraCallInfo		SEQUENCE OF AliasAddress OPTIONAL,
-- 	destinationType			EndpointType OPTIONAL,
-- 	remoteExtensionAddress	SEQUENCE OF AliasAddress OPTIONAL,
-- 	alternateEndpoints		SEQUENCE OF Endpoint OPTIONAL,
-- 	tokens					SEQUENCE OF ClearToken OPTIONAL,
-- 	cryptoTokens			SEQUENCE OF CryptoH323Token OPTIONAL,
-- 	integrityCheckValue		ICV OPTIONAL,
-- 	transportQOS			TransportQOS OPTIONAL,
-- 	willRespondToIRR		BOOLEAN,
-- 	uuiesRequested			UUIEsRequested 
-- }
-- ------------------------------------------------------------- --

--<ASN1.PDU
--		H323-MESSAGES.AdmissionConfirm>--
--<OSS.TYPENAME 
--		H323-MESSAGES.AdmissionConfirm
--		"EmACF">--
--<OSS.FIELDNAME 
--		H323-MESSAGES.AdmissionConfirm.requestSeqNum
--		"requestSeqNum">--
--<OSS.FIELDNAME 
--		H323-MESSAGES.AdmissionConfirm.bandWidth
--		"bandWidth">--
--<OSS.FIELDNAME 
--		H323-MESSAGES.AdmissionConfirm.callModel
--		"callModel">--
--<OSS.FIELDNAME 
--		H323-MESSAGES.AdmissionConfirm.destCallSignalAddress
--		"destCallSignalAddress">--
--<OSS.FIELDNAME 
--		H323-MESSAGES.AdmissionConfirm.irrFrequency
--		"irrFrequency">--
--<OSS.DefineName
--		H323-MESSAGES.AdmissionConfirm.irrFrequency
--		"EM_irrFrequency">--
--<OSS.FIELDNAME 
--		H323-MESSAGES.AdmissionConfirm.nonStandardData
--		"nonStandardData">--
--<OSS.DefineName
--		H323-MESSAGES.AdmissionConfirm.nonStandardData
--		"EM_ACF_nonStandardData">--
--<OSS.FIELDNAME 
--		H323-MESSAGES.AdmissionConfirm.destinationInfo
--		"destinationInfo">--
--<OSS.DefineName
--		H323-MESSAGES.AdmissionConfirm.destinationInfo
--		"EM_ACF_destinationInfo">--
--<OSS.FIELDNAME 
--		H323-MESSAGES.AdmissionConfirm.destExtraCallInfo
--		"destExtraCallInfo">--
--<OSS.DefineName
--		H323-MESSAGES.AdmissionConfirm.destExtraCallInfo
--		"EM_ACF_destExtraCallInfo">--
--<OSS.FIELDNAME 
--		H323-MESSAGES.AdmissionConfirm.destinationType
--		"destinationType">--
--<OSS.DefineName
--		H323-MESSAGES.AdmissionConfirm.destinationType
--		"EM_ACF_destinationType">--
--<OSS.FIELDNAME 
--		H323-MESSAGES.AdmissionConfirm.remoteExtensionAddress
--		"remoteExtensionAddress">--
--<OSS.DefineName
--		H323-MESSAGES.AdmissionConfirm.remoteExtensionAddress
--		"EM_ACF_remoteExtensionAddress">--
--<OSS.FIELDNAME 
--		H323-MESSAGES.AdmissionConfirm.alternateEndpoints
--		"alternateEndpoints">--
--<OSS.DefineName
--		H323-MESSAGES.AdmissionConfirm.alternateEndpoints
--		"EM_ACF_alternateEndpoints">--
--<OSS.FIELDNAME 
--		H323-MESSAGES.AdmissionConfirm.tokens
--		"tokens">--
--<OSS.DefineName
--		H323-MESSAGES.AdmissionConfirm.tokens
--		"EM_ACF_tokens">--
--<OSS.FIELDNAME 
--		H323-MESSAGES.AdmissionConfirm.cryptoTokens
--		"cryptoTokens">--
--<OSS.DefineName
--		H323-MESSAGES.AdmissionConfirm.cryptoTokens
--		"EM_ACF_cryptoTokens">--
--<OSS.FIELDNAME 
--		H323-MESSAGES.AdmissionConfirm.integrityCheckValue
--		"integrityCheckValue">--
--<OSS.DefineName
--		H323-MESSAGES.AdmissionConfirm.integrityCheckValue
--		"EM_ACF_integrityCheckValue">--
--<OSS.FIELDNAME 
--		H323-MESSAGES.AdmissionConfirm.transportQOS
--		"transportQOS">--
--<OSS.DefineName
--		H323-MESSAGES.AdmissionConfirm.transportQOS
--		"EM_ACF_transportQOS">--
--<OSS.FIELDNAME 
--		H323-MESSAGES.AdmissionConfirm.willRespondToIRR
--		"willRespondToIRR">--
--<OSS.DefineName
--		H323-MESSAGES.AdmissionConfirm.willRespondToIRR
--		"EM_ACF_willRespondToIRR">--
--<OSS.FIELDNAME 
--		H323-MESSAGES.AdmissionConfirm.uuiesRequested
--		"uuiesRequested">--
--<OSS.DefineName
--		H323-MESSAGES.AdmissionConfirm.uuiesRequested
--		"EM_ACF_uuiesRequested">--

-- ------------------------------------------------------------- --
-- UUIEsRequested ::= SEQUENCE
-- {
-- 	setup			BOOLEAN,
-- 	callProceeding	BOOLEAN,
-- 	connect			BOOLEAN,
-- 	alerting		BOOLEAN,
-- 	information		BOOLEAN,
-- 	releaseComplete	BOOLEAN,
-- 	facility		BOOLEAN,
-- 	progress		BOOLEAN,
-- 	empty			BOOLEAN,
-- 	...
-- }
-- ------------------------------------------------------------- --

--<ASN1.PDU
--		H323-MESSAGES.UUIEsRequested>--
--<OSS.TYPENAME 
--		H323-MESSAGES.UUIEsRequested
--		"EmUUIEsRequested">--
--<OSS.FIELDNAME 
--		H323-MESSAGES.UUIEsRequested.setup
--		"setup">--
--<OSS.FIELDNAME 
--		H323-MESSAGES.UUIEsRequested.callProceeding
--		"callProceeding">--
--<OSS.FIELDNAME 
--		H323-MESSAGES.UUIEsRequested.connect
--		"connect">--
--<OSS.FIELDNAME 
--		H323-MESSAGES.UUIEsRequested.alerting
--		"alerting">--
--<OSS.FIELDNAME 
--		H323-MESSAGES.UUIEsRequested.information
--		"information">--
--<OSS.FIELDNAME 
--		H323-MESSAGES.UUIEsRequested.releaseComplete
--		"releaseComplete">--
--<OSS.FIELDNAME 
--		H323-MESSAGES.UUIEsRequested.facility
--		"facility">--
--<OSS.FIELDNAME 
--		H323-MESSAGES.UUIEsRequested.progress
--		"progress">--
--<OSS.FIELDNAME 
--		H323-MESSAGES.UUIEsRequested.empty
--		"empty">--

-- ------------------------------------------------------------- --
-- AdmissionReject ::= SEQUENCE 
-- {
-- 	requestSeqNum		RequestSeqNum,
-- 	rejectReason		AdmissionRejectReason,
-- 	nonStandardData		NonStandardParameter OPTIONAL,
-- 	...,
-- 	altGKInfo			AltGKInfo OPTIONAL,
-- 	tokens				SEQUENCE OF ClearToken OPTIONAL,
-- 	cryptoTokens		SEQUENCE OF CryptoH323Token OPTIONAL,
-- 	callSignalAddress	SEQUENCE OF TransportAddress OPTIONAL,
-- 	integrityCheckValue	ICV OPTIONAL
-- }
-- ------------------------------------------------------------- --

--<ASN1.PDU
--		H323-MESSAGES.AdmissionReject>--
--<OSS.TYPENAME 
--		H323-MESSAGES.AdmissionReject
--		"EmARJ">--
--<OSS.FIELDNAME 
--		H323-MESSAGES.AdmissionReject.requestSeqNum
--		"requestSeqNum">--
--<OSS.FIELDNAME 
--		H323-MESSAGES.AdmissionReject.rejectReason
--		"rejectReason">--
--<OSS.FIELDNAME 
--		H323-MESSAGES.AdmissionReject.nonStandardData
--		"nonStandardData">--
--<OSS.DefineName
--		H323-MESSAGES.AdmissionReject.nonStandardData
--		"EM_ARJ_nonStandardData">--
--<OSS.FIELDNAME 
--		H323-MESSAGES.AdmissionReject.altGKInfo
--		"altGKInfo">--
--<OSS.DefineName
--		H323-MESSAGES.AdmissionReject.altGKInfo
--		"EM_ARJ_altGKInfo">--
--<OSS.FIELDNAME 
--		H323-MESSAGES.AdmissionReject.tokens
--		"tokens">--
--<OSS.DefineName
--		H323-MESSAGES.AdmissionReject.tokens
--		"EM_ARJ_tokens">--
--<OSS.FIELDNAME 
--		H323-MESSAGES.AdmissionReject.cryptoTokens
--		"cryptoTokens">--
--<OSS.DefineName
--		H323-MESSAGES.AdmissionReject.cryptoTokens
--		"EM_ARJ_cryptoTokens">--
--<OSS.FIELDNAME 
--		H323-MESSAGES.AdmissionReject.callSignalAddress
--		"callSignalAddress">--
--<OSS.DefineName
--		H323-MESSAGES.AdmissionReject.callSignalAddress
--		"EM_ARJ_callSignalAddress">--
--<OSS.FIELDNAME 
--		H323-MESSAGES.AdmissionReject.integrityCheckValue
--		"integrityCheckValue">--
--<OSS.DefineName
--		H323-MESSAGES.AdmissionReject.integrityCheckValue
--		"EM_ARJ_integrityCheckValue">--

-- ------------------------------------------------------------- --
-- AdmissionRejectReason ::= CHOICE
-- {
-- 	calledPartyNotRegistered	NULL,	
-- 	invalidPermission			NULL,	
-- 	requestDenied				NULL,	
-- 	undefinedReason				NULL,
-- 	callerNotRegistered			NULL,
-- 	routeCallToGatekeeper		NULL,
-- 	invalidEndpointIdentifier	NULL,
-- 	resourceUnavailable			NULL,
-- 	...,
-- 	securityDenial				NULL,
-- 	qosControlNotSupported		NULL,
-- 	incompleteAddress			NULL
-- }
-- ------------------------------------------------------------- --

--<ASN1.PDU
--		H323-MESSAGES.AdmissionRejectReason>--
--<OSS.TYPENAME 
--		H323-MESSAGES.AdmissionRejectReason
--		"EmARJReason">--
--<OSS.FIELDNAME 
--		H323-MESSAGES.AdmissionRejectReason.calledPartyNotRegistered
--		"calledPartyNotRegistered">--
--<OSS.DefineName
--		H323-MESSAGES.AdmissionRejectReason.calledPartyNotRegistered
--		"EM_ARJ_calledPartyNotRegistered">--
--<OSS.FIELDNAME 
--		H323-MESSAGES.AdmissionRejectReason.invalidPermission
--		"invalidPermission">--
--<OSS.DefineName
--		H323-MESSAGES.AdmissionRejectReason.invalidPermission
--		"EM_ARJ_invalidPermission">--
--<OSS.FIELDNAME 
--		H323-MESSAGES.AdmissionRejectReason.requestDenied
--		"requestDenied">--
--<OSS.DefineName
--		H323-MESSAGES.AdmissionRejectReason.requestDenied
--		"EM_ARJ_requestDenied">--
--<OSS.FIELDNAME 
--		H323-MESSAGES.AdmissionRejectReason.undefinedReason
--		"undefinedReason">--
--<OSS.DefineName
--		H323-MESSAGES.AdmissionRejectReason.undefinedReason
--		"EM_ARJ_undefinedReason">--
--<OSS.FIELDNAME 
--		H323-MESSAGES.AdmissionRejectReason.callerNotRegistered
--		"callerNotRegistered">--
--<OSS.DefineName
--		H323-MESSAGES.AdmissionRejectReason.callerNotRegistered
--		"EM_callerNotRegistered">--
--<OSS.FIELDNAME 
--		H323-MESSAGES.AdmissionRejectReason.routeCallToGatekeeper
--		"routeCallToGatekeeper">--
--<OSS.DefineName
--		H323-MESSAGES.AdmissionRejectReason.routeCallToGatekeeper
--		"EM_ARJ_routeCallToGatekeeper">--
--<OSS.FIELDNAME 
--		H323-MESSAGES.AdmissionRejectReason.invalidEndpointIdentifier
--		"invalidEndpointIdentifier">--
--<OSS.DefineName
--		H323-MESSAGES.AdmissionRejectReason.invalidEndpointIdentifier
--		"EM_invalidEndpointIdentifier">--
--<OSS.FIELDNAME 
--		H323-MESSAGES.AdmissionRejectReason.resourceUnavailable
--		"resourceUnavailable">--
--<OSS.DefineName
--		H323-MESSAGES.AdmissionRejectReason.resourceUnavailable
--		"EM_ARJ_resourceUnavailable">--
--<OSS.FIELDNAME 
--		H323-MESSAGES.AdmissionRejectReason.securityDenial
--		"securityDenial">--
--<OSS.DefineName
--		H323-MESSAGES.AdmissionRejectReason.securityDenial
--		"EM_ARJ_securityDenial">--
--<OSS.FIELDNAME 
--		H323-MESSAGES.AdmissionRejectReason.qosControlNotSupported
--		"qosControlNotSupported">--
--<OSS.DefineName
--		H323-MESSAGES.AdmissionRejectReason.qosControlNotSupported
--		"EM_qosControlNotSupported">--
--<OSS.FIELDNAME 
--		H323-MESSAGES.AdmissionRejectReason.incompleteAddress
--		"incompleteAddress">--
--<OSS.DefineName
--		H323-MESSAGES.AdmissionRejectReason.incompleteAddress
--		"EM_incompleteAddress">--

-- ------------------------------------------------------------- --
-- BandwidthRequest ::= SEQUENCE 
-- {
-- 	requestSeqNum			RequestSeqNum,
-- 	endpointIdentifier		EndpointIdentifier,
-- 	conferenceID			ConferenceIdentifier,
-- 	callReferenceValue		CallReferenceValue,
-- 	callType				CallType OPTIONAL,
-- 	bandWidth				BandWidth,
-- 	nonStandardData			NonStandardParameter OPTIONAL,
-- 	...,
-- 	callIdentifier			CallIdentifier,
-- 	gatekeeperIdentifier	GatekeeperIdentifier OPTIONAL,
-- 	tokens					SEQUENCE OF ClearToken OPTIONAL,
-- 	cryptoTokens			SEQUENCE OF CryptoH323Token OPTIONAL,
-- 	integrityCheckValue		ICV OPTIONAL,
-- 	answeredCall			BOOLEAN
-- }
-- ------------------------------------------------------------- --

--<ASN1.PDU
--		H323-MESSAGES.BandwidthRequest>--
--<OSS.TYPENAME 
--		H323-MESSAGES.BandwidthRequest
--		"EmBRQ">--
--<OSS.FIELDNAME 
--		H323-MESSAGES.BandwidthRequest.requestSeqNum
--		"requestSeqNum">--
--<OSS.FIELDNAME 
--		H323-MESSAGES.BandwidthRequest.endpointIdentifier
--		"endpointIdentifier">--
--<OSS.FIELDNAME 
--		H323-MESSAGES.BandwidthRequest.conferenceID
--		"conferenceID">--
--<OSS.FIELDNAME 
--		H323-MESSAGES.BandwidthRequest.callReferenceValue
--		"callReferenceValue">--
--<OSS.FIELDNAME 
--		H323-MESSAGES.BandwidthRequest.callType
--		"callType">--
--<OSS.DefineName
--		H323-MESSAGES.BandwidthRequest.callType
--		"EM_callType">--
--<OSS.FIELDNAME 
--		H323-MESSAGES.BandwidthRequest.bandWidth
--		"bandWidth">--
--<OSS.FIELDNAME 
--		H323-MESSAGES.BandwidthRequest.nonStandardData
--		"nonStandardData">--
--<OSS.DefineName
--		H323-MESSAGES.BandwidthRequest.nonStandardData
--		"EM_BRQ_nonStandardData">--
--<OSS.FIELDNAME 
--		H323-MESSAGES.BandwidthRequest.callIdentifier
--		"callIdentifier">--
--<OSS.DefineName
--		H323-MESSAGES.BandwidthRequest.callIdentifier
--		"EM_BRQ_callIdentifier">--
--<OSS.FIELDNAME 
--		H323-MESSAGES.BandwidthRequest.gatekeeperIdentifier
--		"gatekeeperIdentifier">--
--<OSS.DefineName
--		H323-MESSAGES.BandwidthRequest.gatekeeperIdentifier
--		"EM_BRQ_gatekeeperIdentifier">--
--<OSS.FIELDNAME 
--		H323-MESSAGES.BandwidthRequest.tokens
--		"tokens">--
--<OSS.DefineName
--		H323-MESSAGES.BandwidthRequest.tokens
--		"EM_BRQ_tokens">--
--<OSS.FIELDNAME 
--		H323-MESSAGES.BandwidthRequest.cryptoTokens
--		"cryptoTokens">--
--<OSS.DefineName
--		H323-MESSAGES.BandwidthRequest.cryptoTokens
--		"EM_BRQ_cryptoTokens">--
--<OSS.FIELDNAME 
--		H323-MESSAGES.BandwidthRequest.integrityCheckValue
--		"integrityCheckValue">--
--<OSS.DefineName
--		H323-MESSAGES.BandwidthRequest.integrityCheckValue
--		"EM_BRQ_integrityCheckValue">--
--<OSS.FIELDNAME 
--		H323-MESSAGES.BandwidthRequest.answeredCall
--		"answeredCall">--
--<OSS.DefineName
--		H323-MESSAGES.BandwidthRequest.answeredCall
--		"EM_BRQ_answeredCall">--

-- ------------------------------------------------------------- --
-- BandwidthConfirm ::= SEQUENCE 
-- {
-- 	requestSeqNum		RequestSeqNum,
-- 	bandWidth			BandWidth,
-- 	nonStandardData		NonStandardParameter OPTIONAL,
-- 	...,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.BandwidthConfirm>--
--<OSS.TYPENAME 
--		H323-MESSAGES.BandwidthConfirm
--		"EmBCF">--
--<OSS.FIELDNAME 
--		H323-MESSAGES.BandwidthConfirm.requestSeqNum
--		"requestSeqNum">--
--<OSS.FIELDNAME 
--		H323-MESSAGES.BandwidthConfirm.bandWidth
--		"bandWidth">--
--<OSS.FIELDNAME 
--		H323-MESSAGES.BandwidthConfirm.nonStandardData
--		"nonStandardData">--
--<OSS.DefineName
--		H323-MESSAGES.BandwidthConfirm.nonStandardData
--		"EM_BCF_nonStandardData">--
--<OSS.FIELDNAME 
--		H323-MESSAGES.BandwidthConfirm.tokens
--		"tokens">--
--<OSS.DefineName
--		H323-MESSAGES.BandwidthConfirm.tokens
--		"EM_BCF_tokens">--
--<OSS.FIELDNAME 
--		H323-MESSAGES.BandwidthConfirm.cryptoTokens
--		"cryptoTokens">--
--<OSS.DefineName
--		H323-MESSAGES.BandwidthConfirm.cryptoTokens
--		"EM_BCF_cryptoTokens">--
--<OSS.FIELDNAME 
--		H323-MESSAGES.BandwidthConfirm.integrityCheckValue
--		"integrityCheckValue">--
--<OSS.DefineName
--		H323-MESSAGES.BandwidthConfirm.integrityCheckValue
--		"EM_BCF_integrityCheckValue">--

-- ------------------------------------------------------------- --
-- BandwidthReject ::= SEQUENCE 
-- {
-- 	requestSeqNum		RequestSeqNum,
-- 	rejectReason		BandRejectReason,
-- 	allowedBandWidth	BandWidth,
-- 	nonStandardData		NonStandardParameter OPTIONAL,
-- 	...,
-- 	altGKInfo			AltGKInfo OPTIONAL,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.BandwidthReject>--
--<OSS.TYPENAME 
--		H323-MESSAGES.BandwidthReject
--		"EmBRJ">--
--<OSS.FIELDNAME 
--		H323-MESSAGES.BandwidthReject.requestSeqNum
--		"requestSeqNum">--
--<OSS.FIELDNAME 
--		H323-MESSAGES.BandwidthReject.rejectReason
--		"rejectReason">--
--<OSS.FIELDNAME 
--		H323-MESSAGES.BandwidthReject.allowedBandWidth
--		"allowedBandWidth">--
--<OSS.FIELDNAME 
--		H323-MESSAGES.BandwidthReject.nonStandardData
--		"nonStandardData">--
--<OSS.DefineName
--		H323-MESSAGES.BandwidthReject.nonStandardData
--		"EM_BRJ_nonStandardData">--
--<OSS.FIELDNAME 
--		H323-MESSAGES.BandwidthReject.altGKInfo
--		"altGKInfo">--
--<OSS.DefineName
--		H323-MESSAGES.BandwidthReject.altGKInfo
--		"EM_BRJ_altGKInfo">--
--<OSS.FIELDNAME 
--		H323-MESSAGES.BandwidthReject.tokens
--		"tokens">--
--<OSS.DefineName
--		H323-MESSAGES.BandwidthReject.tokens
--		"EM_BRJ_tokens">--
--<OSS.FIELDNAME 
--		H323-MESSAGES.BandwidthReject.cryptoTokens
--		"cryptoTokens">--
--<OSS.DefineName
--		H323-MESSAGES.BandwidthReject.cryptoTokens
--		"EM_BRJ_cryptoTokens">--
--<OSS.FIELDNAME 
--		H323-MESSAGES.BandwidthReject.integrityCheckValue
--		"integrityCheckValue">--
--<OSS.DefineName
--		H323-MESSAGES.BandwidthReject.integrityCheckValue
--		"EM_BRJ_integrityCheckValue">--

-- ------------------------------------------------------------- --
-- BandRejectReason ::= CHOICE
-- {
-- 	notBound				NULL,	
-- 	invalidConferenceID		NULL,	
-- 	invalidPermission		NULL,	
-- 	insufficientResources	NULL,
-- 	invalidRevision			NULL,
-- 	undefinedReason			NULL,
-- 	...,
-- 	securityDenial			NULL
-- }
-- ------------------------------------------------------------- --

--<ASN1.PDU
--		H323-MESSAGES.BandRejectReason>--
--<OSS.TYPENAME 
--		H323-MESSAGES.BandRejectReason
--		"EmBRJReason">--
--<OSS.FIELDNAME 
--		H323-MESSAGES.BandRejectReason.notBound
--		"notBound">--
--<OSS.DefineName
--		H323-MESSAGES.BandRejectReason.notBound
--		"EM_notBound">--
--<OSS.FIELDNAME 
--		H323-MESSAGES.BandRejectReason.invalidConferenceID
--		"invalidConferenceID">--
--<OSS.DefineName
--		H323-MESSAGES.BandRejectReason.invalidConferenceID
--		"EM_invalidConferenceID">--
--<OSS.FIELDNAME 
--		H323-MESSAGES.BandRejectReason.invalidPermission
--		"invalidPermission">--
--<OSS.DefineName
--		H323-MESSAGES.BandRejectReason.invalidPermission
--		"EM_BRJ_invalidPermission">--
--<OSS.FIELDNAME 
--		H323-MESSAGES.BandRejectReason.insufficientResources
--		"insufficientResources">--
--<OSS.DefineName
--		H323-MESSAGES.BandRejectReason.insufficientResources
--		"EM_insufficientResources">--
--<OSS.FIELDNAME 
--		H323-MESSAGES.BandRejectReason.invalidRevision
--		"invalidRevision">--
--<OSS.DefineName
--		H323-MESSAGES.BandRejectReason.invalidRevision
--		"EM_BRJ_invalidRevision">--
--<OSS.FIELDNAME 
--		H323-MESSAGES.BandRejectReason.undefinedReason
--		"undefinedReason">--
--<OSS.DefineName
--		H323-MESSAGES.BandRejectReason.undefinedReason
--		"EM_BRJ_undefinedReason">--
--<OSS.FIELDNAME 
--		H323-MESSAGES.BandRejectReason.securityDenial
--		"securityDenial">--
--<OSS.DefineName
--		H323-MESSAGES.BandRejectReason.securityDenial
--		"EM_BRJ_securityDenial">--

-- ------------------------------------------------------------- --
-- LocationRequest ::= SEQUENCE 
-- {
-- 	requestSeqNum			RequestSeqNum,
-- 	endpointIdentifier		EndpointIdentifier OPTIONAL,
-- 	destinationInfo			SEQUENCE OF AliasAddress,
-- 	nonStandardData			NonStandardParameter OPTIONAL,
-- 	replyAddress			TransportAddress,
-- 	...,
-- 	sourceInfo				SEQUENCE OF AliasAddress OPTIONAL,
-- 	canMapAlias				BOOLEAN,	
-- 	gatekeeperIdentifier	GatekeeperIdentifier OPTIONAL,
-- 	tokens					SEQUENCE OF ClearToken OPTIONAL,
-- 	cryptoTokens			SEQUENCE OF CryptoH323Token OPTIONAL,
-- 	integrityCheckValue		ICV OPTIONAL
-- }
-- ------------------------------------------------------------- --

--<ASN1.PDU
--		H323-MESSAGES.LocationRequest>--
--<OSS.TYPENAME 
--		H323-MESSAGES.LocationRequest
--		"EmLRQ">--
--<OSS.FIELDNAME 
--		H323-MESSAGES.LocationRequest.requestSeqNum
--		"requestSeqNum">--
--<OSS.FIELDNAME 
--		H323-MESSAGES.LocationRequest.endpointIdentifier
--		"endpointIdentifier">--
--<OSS.DefineName
--		H323-MESSAGES.LocationRequest.endpointIdentifier
--		"EM_LRQ_endpointIdentifier">--
--<OSS.FIELDNAME 
--		H323-MESSAGES.LocationRequest.destinationInfo
--		"destinationInfo">--
--<OSS.FIELDNAME 
--		H323-MESSAGES.LocationRequest.nonStandardData
--		"nonStandardData">--
--<OSS.DefineName
--		H323-MESSAGES.LocationRequest.nonStandardData
--		"EM_LRQ_nonStandardData">--
--<OSS.FIELDNAME 
--		H323-MESSAGES.LocationRequest.replyAddress
--		"replyAddress">--
--<OSS.FIELDNAME 
--		H323-MESSAGES.LocationRequest.sourceInfo
--		"sourceInfo">--
--<OSS.DefineName
--		H323-MESSAGES.LocationRequest.sourceInfo
--		"EM_sourceInfo">--
--<OSS.FIELDNAME 
--		H323-MESSAGES.LocationRequest.canMapAlias
--		"canMapAlias">--
--<OSS.DefineName
--		H323-MESSAGES.LocationRequest.canMapAlias
--		"EM_LRQ_canMapAlias">--
--<OSS.FIELDNAME 
--		H323-MESSAGES.LocationRequest.gatekeeperIdentifier
--		"gatekeeperIdentifier">--
--<OSS.DefineName
--		H323-MESSAGES.LocationRequest.gatekeeperIdentifier
--		"EM_LRQ_gatekeeperIdentifier">--
--<OSS.FIELDNAME 
--		H323-MESSAGES.LocationRequest.tokens
--		"tokens">--
--<OSS.DefineName
--		H323-MESSAGES.LocationRequest.tokens
--		"EM_LRQ_tokens">--
--<OSS.FIELDNAME 
--		H323-MESSAGES.LocationRequest.cryptoTokens
--		"cryptoTokens">--
--<OSS.DefineName
--		H323-MESSAGES.LocationRequest.cryptoTokens
--		"EM_LRQ_cryptoTokens">--
--<OSS.FIELDNAME 
--		H323-MESSAGES.LocationRequest.integrityCheckValue
--		"integrityCheckValue">--
--<OSS.DefineName
--		H323-MESSAGES.LocationRequest.integrityCheckValue
--		"EM_LRQ_integrityCheckValue">--

-- ------------------------------------------------------------- --
-- LocationConfirm ::= SEQUENCE 
-- {
-- 	requestSeqNum			RequestSeqNum,
-- 	callSignalAddress		TransportAddress,
-- 	rasAddress				TransportAddress,
-- 	nonStandardData			NonStandardParameter OPTIONAL,
-- 	...,
-- 	destinationInfo			SEQUENCE OF AliasAddress OPTIONAL,
-- 	destExtraCallInfo		SEQUENCE OF AliasAddress OPTIONAL,
-- 	destinationType			EndpointType OPTIONAL,
-- 	remoteExtensionAddress	SEQUENCE OF AliasAddress OPTIONAL,
-- 	alternateEndpoints		SEQUENCE OF Endpoint OPTIONAL,
-- 	tokens					SEQUENCE OF ClearToken OPTIONAL,
-- 	cryptoTokens			SEQUENCE OF CryptoH323Token OPTIONAL,
-- 	integrityCheckValue		ICV OPTIONAL
-- }
-- ------------------------------------------------------------- --

--<ASN1.PDU
--		H323-MESSAGES.LocationConfirm>--
--<OSS.TYPENAME 
--		H323-MESSAGES.LocationConfirm
--		"EmLCF">--
--<OSS.FIELDNAME 
--		H323-MESSAGES.LocationConfirm.requestSeqNum
--		"requestSeqNum">--
--<OSS.FIELDNAME 
--		H323-MESSAGES.LocationConfirm.callSignalAddress
--		"callSignalAddress">--
--<OSS.FIELDNAME 
--		H323-MESSAGES.LocationConfirm.rasAddress
--		"rasAddress">--
--<OSS.FIELDNAME 
--		H323-MESSAGES.LocationConfirm.nonStandardData
--		"nonStandardData">--
--<OSS.DefineName
--		H323-MESSAGES.LocationConfirm.nonStandardData
--		"EM_LCF_nonStandardData">--
--<OSS.FIELDNAME 
--		H323-MESSAGES.LocationConfirm.destinationInfo
--		"destinationInfo">--
--<OSS.DefineName
--		H323-MESSAGES.LocationConfirm.destinationInfo
--		"EM_LCF_destinationInfo">--
--<OSS.FIELDNAME 
--		H323-MESSAGES.LocationConfirm.destExtraCallInfo
--		"destExtraCallInfo">--
--<OSS.DefineName
--		H323-MESSAGES.LocationConfirm.destExtraCallInfo
--		"EM_LCF_destExtraCallInfo">--
--<OSS.FIELDNAME 
--		H323-MESSAGES.LocationConfirm.destinationType
--		"destinationType">--
--<OSS.DefineName
--		H323-MESSAGES.LocationConfirm.destinationType
--		"EM_LCF_destinationType">--
--<OSS.FIELDNAME 
--		H323-MESSAGES.LocationConfirm.remoteExtensionAddress
--		"remoteExtensionAddress">--
--<OSS.DefineName
--		H323-MESSAGES.LocationConfirm.remoteExtensionAddress
--		"EM_LCF_remoteExtensionAddress">--
--<OSS.FIELDNAME 
--		H323-MESSAGES.LocationConfirm.alternateEndpoints
--		"alternateEndpoints">--
--<OSS.DefineName
--		H323-MESSAGES.LocationConfirm.alternateEndpoints
--		"EM_LCF_alternateEndpoints">--
--<OSS.FIELDNAME 
--		H323-MESSAGES.LocationConfirm.tokens
--		"tokens">--
--<OSS.DefineName
--		H323-MESSAGES.LocationConfirm.tokens
--		"EM_LCF_tokens">--
--<OSS.FIELDNAME 
--		H323-MESSAGES.LocationConfirm.cryptoTokens
--		"cryptoTokens">--
--<OSS.DefineName
--		H323-MESSAGES.LocationConfirm.cryptoTokens
--		"EM_LCF_cryptoTokens">--
--<OSS.FIELDNAME 
--		H323-MESSAGES.LocationConfirm.integrityCheckValue
--		"integrityCheckValue">--
--<OSS.DefineName
--		H323-MESSAGES.LocationConfirm.integrityCheckValue
--		"EM_LCF_integrityCheckValue">--

-- ------------------------------------------------------------- --
-- LocationReject ::= SEQUENCE 
-- {
-- 	requestSeqNum		RequestSeqNum,
-- 	rejectReason		LocationRejectReason,
-- 	nonStandardData		NonStandardParameter OPTIONAL,
-- 	...,
-- 	altGKInfo			AltGKInfo OPTIONAL,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.LocationReject>--
--<OSS.TYPENAME 
--		H323-MESSAGES.LocationReject
--		"EmLRJ">--
--<OSS.FIELDNAME 
--		H323-MESSAGES.LocationReject.requestSeqNum
--		"requestSeqNum">--
--<OSS.FIELDNAME 
--		H323-MESSAGES.LocationReject.rejectReason
--		"rejectReason">--
--<OSS.FIELDNAME 
--		H323-MESSAGES.LocationReject.nonStandardData
--		"nonStandardData">--
--<OSS.DefineName
--		H323-MESSAGES.LocationReject.nonStandardData
--		"EM_LRJ_nonStandardData">--
--<OSS.FIELDNAME 
--		H323-MESSAGES.LocationReject.altGKInfo
--		"altGKInfo">--
--<OSS.DefineName
--		H323-MESSAGES.LocationReject.altGKInfo
--		"EM_LRJ_altGKInfo">--
--<OSS.FIELDNAME 
--		H323-MESSAGES.LocationReject.tokens
--		"tokens">--
--<OSS.DefineName
--		H323-MESSAGES.LocationReject.tokens
--		"EM_LRJ_tokens">--
--<OSS.FIELDNAME 
--		H323-MESSAGES.LocationReject.cryptoTokens
--		"cryptoTokens">--
--<OSS.DefineName
--		H323-MESSAGES.LocationReject.cryptoTokens
--		"EM_LRJ_cryptoTokens">--
--<OSS.FIELDNAME 
--		H323-MESSAGES.LocationReject.integrityCheckValue
--		"integrityCheckValue">--
--<OSS.DefineName
--		H323-MESSAGES.LocationReject.integrityCheckValue
--		"EM_LRJ_integrityCheckValue">--

-- ------------------------------------------------------------- --
-- LocationRejectReason ::= CHOICE
-- {
-- 	notRegistered		NULL,
-- 	invalidPermission	NULL,
-- 	requestDenied		NULL,
-- 	undefinedReason		NULL,
-- 	...,
-- 	securityDenial		NULL
-- }
-- ------------------------------------------------------------- --

--<ASN1.PDU
--		H323-MESSAGES.LocationRejectReason>--
--<OSS.TYPENAME 
--		H323-MESSAGES.LocationRejectReason
--		"EmLRJReason">--
--<OSS.FIELDNAME 
--		H323-MESSAGES.LocationRejectReason.notRegistered
--		"notRegistered">--
--<OSS.DefineName
--		H323-MESSAGES.LocationRejectReason.notRegistered
--		"EM_LRJ_notRegistered">--
--<OSS.FIELDNAME 
--		H323-MESSAGES.LocationRejectReason.invalidPermission
--		"invalidPermission">--
--<OSS.DefineName
--		H323-MESSAGES.LocationRejectReason.invalidPermission
--		"EM_invalidPermission">--
--<OSS.FIELDNAME 
--		H323-MESSAGES.LocationRejectReason.requestDenied
--		"requestDenied">--
--<OSS.DefineName
--		H323-MESSAGES.LocationRejectReason.requestDenied
--		"EM_LRJ_requestDenied">--
--<OSS.FIELDNAME 
--		H323-MESSAGES.LocationRejectReason.undefinedReason
--		"undefinedReason">--
--<OSS.DefineName
--		H323-MESSAGES.LocationRejectReason.undefinedReason
--		"EM_LRJ_undefinedReason">--
--<OSS.FIELDNAME 
--		H323-MESSAGES.LocationRejectReason.securityDenial
--		"securityDenial">--
--<OSS.DefineName
--		H323-MESSAGES.LocationRejectReason.securityDenial
--		"EM_LRJ_securityDenial">--

-- ------------------------------------------------------------- --
-- DisengageRequest ::= SEQUENCE
-- {
-- 	requestSeqNum			RequestSeqNum,
-- 	endpointIdentifier		EndpointIdentifier,
-- 	conferenceID			ConferenceIdentifier,
-- 	callReferenceValue		CallReferenceValue,
-- 	disengageReason			DisengageReason,
-- 	nonStandardData			NonStandardParameter OPTIONAL,
-- 	...,
-- 	callIdentifier			CallIdentifier,
-- 	gatekeeperIdentifier	GatekeeperIdentifier OPTIONAL,
-- 	tokens					SEQUENCE OF ClearToken OPTIONAL,
-- 	cryptoTokens			SEQUENCE OF CryptoH323Token OPTIONAL,
-- 	integrityCheckValue		ICV OPTIONAL,
-- 	answeredCall			BOOLEAN
-- }
-- ------------------------------------------------------------- --

--<ASN1.PDU
--		H323-MESSAGES.DisengageRequest>--
--<OSS.TYPENAME 
--		H323-MESSAGES.DisengageRequest
--		"EmDRQ">--
--<OSS.FIELDNAME 
--		H323-MESSAGES.DisengageRequest.requestSeqNum
--		"requestSeqNum">--
--<OSS.FIELDNAME 
--		H323-MESSAGES.DisengageRequest.endpointIdentifier
--		"endpointIdentifier">--
--<OSS.FIELDNAME 
--		H323-MESSAGES.DisengageRequest.conferenceID
--		"conferenceID">--
--<OSS.FIELDNAME 
--		H323-MESSAGES.DisengageRequest.callReferenceValue
--		"callReferenceValue">--
--<OSS.FIELDNAME 
--		H323-MESSAGES.DisengageRequest.disengageReason
--		"disengageReason">--
--<OSS.FIELDNAME 
--		H323-MESSAGES.DisengageRequest.nonStandardData
--		"nonStandardData">--
--<OSS.DefineName
--		H323-MESSAGES.DisengageRequest.nonStandardData
--		"EM_DRQ_nonStandardData">--
--<OSS.FIELDNAME 
--		H323-MESSAGES.DisengageRequest.callIdentifier
--		"callIdentifier">--
--<OSS.DefineName
--		H323-MESSAGES.DisengageRequest.callIdentifier
--		"EM_DRQ_callIdentifier">--
--<OSS.FIELDNAME 
--		H323-MESSAGES.DisengageRequest.gatekeeperIdentifier
--		"gatekeeperIdentifier">--
--<OSS.DefineName
--		H323-MESSAGES.DisengageRequest.gatekeeperIdentifier
--		"EM_DRQ_gatekeeperIdentifier">--
--<OSS.FIELDNAME 
--		H323-MESSAGES.DisengageRequest.tokens
--		"tokens">--
--<OSS.DefineName
--		H323-MESSAGES.DisengageRequest.tokens
--		"EM_DRQ_tokens">--
--<OSS.FIELDNAME 
--		H323-MESSAGES.DisengageRequest.cryptoTokens
--		"cryptoTokens">--
--<OSS.DefineName
--		H323-MESSAGES.DisengageRequest.cryptoTokens
--		"EM_DRQ_cryptoTokens">--
--<OSS.FIELDNAME 
--		H323-MESSAGES.DisengageRequest.integrityCheckValue
--		"integrityCheckValue">--
--<OSS.DefineName
--		H323-MESSAGES.DisengageRequest.integrityCheckValue
--		"EM_DRQ_integrityCheckValue">--
--<OSS.FIELDNAME 
--		H323-MESSAGES.DisengageRequest.answeredCall
--		"answeredCall">--
--<OSS.DefineName
--		H323-MESSAGES.DisengageRequest.answeredCall
--		"EM_DRQ_answeredCall">--

-- ------------------------------------------------------------- --
-- DisengageReason ::= CHOICE
-- {
-- 	forcedDrop		NULL,
-- 	normalDrop		NULL,
-- 	undefinedReason	NULL,
-- 	...
-- }
-- ------------------------------------------------------------- --

--<ASN1.PDU
--		H323-MESSAGES.DisengageReason>--
--<OSS.TYPENAME 
--		H323-MESSAGES.DisengageReason
--		"EmDisengageReason">--
--<OSS.FIELDNAME 
--		H323-MESSAGES.DisengageReason.forcedDrop
--		"forcedDrop">--
--<OSS.DefineName
--		H323-MESSAGES.DisengageReason.forcedDrop
--		"EM_forcedDrop">--
--<OSS.FIELDNAME 
--		H323-MESSAGES.DisengageReason.normalDrop
--		"normalDrop">--
--<OSS.DefineName
--		H323-MESSAGES.DisengageReason.normalDrop
--		"EM_normalDrop">--
--<OSS.FIELDNAME 
--		H323-MESSAGES.DisengageReason.undefinedReason
--		"undefinedReason">--
--<OSS.DefineName
--		H323-MESSAGES.DisengageReason.undefinedReason
--		"EM_DRQ_undefinedReason">--

-- ------------------------------------------------------------- --
-- DisengageConfirm ::= SEQUENCE
-- {
-- 	requestSeqNum		RequestSeqNum,
-- 	nonStandardData		NonStandardParameter OPTIONAL,
-- 	...,
-- 	tokens				SEQUENCE OF ClearToken OPTIONAL,
-- 	cryptoTokens		SEQUENCE OF CryptoH323Token 	 OPTIONAL,
-- 	integrityCheckValue	ICV OPTIONAL
-- }
-- ------------------------------------------------------------- --

--<ASN1.PDU
--		H323-MESSAGES.DisengageConfirm>--
--<OSS.TYPENAME 
--		H323-MESSAGES.DisengageConfirm
--		"EmDCF">--
--<OSS.FIELDNAME 
--		H323-MESSAGES.DisengageConfirm.requestSeqNum
--		"requestSeqNum">--
--<OSS.FIELDNAME 
--		H323-MESSAGES.DisengageConfirm.nonStandardData
--		"nonStandardData">--
--<OSS.DefineName
--		H323-MESSAGES.DisengageConfirm.nonStandardData
--		"EM_DCF_nonStandardData">--
--<OSS.FIELDNAME 
--		H323-MESSAGES.DisengageConfirm.tokens
--		"tokens">--
--<OSS.DefineName
--		H323-MESSAGES.DisengageConfirm.tokens
--		"EM_DCF_tokens">--
--<OSS.FIELDNAME 
--		H323-MESSAGES.DisengageConfirm.cryptoTokens
--		"cryptoTokens">--
--<OSS.DefineName
--		H323-MESSAGES.DisengageConfirm.cryptoTokens
--		"EM_DCF_cryptoTokens">--
--<OSS.FIELDNAME 
--		H323-MESSAGES.DisengageConfirm.integrityCheckValue
--		"integrityCheckValue">--
--<OSS.DefineName
--		H323-MESSAGES.DisengageConfirm.integrityCheckValue
--		"EM_DCF_integrityCheckValue">--

-- ------------------------------------------------------------- --
-- DisengageReject ::= SEQUENCE
-- {
-- 	requestSeqNum		RequestSeqNum,
-- 	rejectReason		DisengageRejectReason,
-- 	nonStandardData		NonStandardParameter OPTIONAL,
-- 	...,
-- 	altGKInfo			AltGKInfo OPTIONAL,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.DisengageReject>--
--<OSS.TYPENAME 
--		H323-MESSAGES.DisengageReject
--		"EmDRJ">--
--<OSS.FIELDNAME 
--		H323-MESSAGES.DisengageReject.requestSeqNum
--		"requestSeqNum">--
--<OSS.FIELDNAME 
--		H323-MESSAGES.DisengageReject.rejectReason
--		"rejectReason">--
--<OSS.FIELDNAME 
--		H323-MESSAGES.DisengageReject.nonStandardData
--		"nonStandardData">--
--<OSS.DefineName
--		H323-MESSAGES.DisengageReject.nonStandardData
--		"EM_DRJ_nonStandardData">--
--<OSS.FIELDNAME 
--		H323-MESSAGES.DisengageReject.altGKInfo
--		"altGKInfo">--
--<OSS.DefineName
--		H323-MESSAGES.DisengageReject.altGKInfo
--		"EM_DRJ_altGKInfo">--
--<OSS.FIELDNAME 
--		H323-MESSAGES.DisengageReject.tokens
--		"tokens">--
--<OSS.DefineName
--		H323-MESSAGES.DisengageReject.tokens
--		"EM_DRJ_tokens">--
--<OSS.FIELDNAME 
--		H323-MESSAGES.DisengageReject.cryptoTokens
--		"cryptoTokens">--
--<OSS.DefineName
--		H323-MESSAGES.DisengageReject.cryptoTokens
--		"EM_DRJ_cryptoTokens">--
--<OSS.FIELDNAME 
--		H323-MESSAGES.DisengageReject.integrityCheckValue
--		"integrityCheckValue">--
--<OSS.DefineName
--		H323-MESSAGES.DisengageReject.integrityCheckValue
--		"EM_DRJ_integrityCheckValue">--

-- ------------------------------------------------------------- --
-- DisengageRejectReason ::= CHOICE
-- {
-- 	notRegistered		NULL,	
-- 	requestToDropOther	NULL, 	
-- 	...,
-- 	securityDenial		NULL
-- }
-- ------------------------------------------------------------- --

--<ASN1.PDU
--		H323-MESSAGES.DisengageRejectReason>--
--<OSS.TYPENAME 
--		H323-MESSAGES.DisengageRejectReason
--		"EmDRJReason">--
--<OSS.FIELDNAME 
--		H323-MESSAGES.DisengageRejectReason.notRegistered
--		"notRegistered">--
--<OSS.DefineName
--		H323-MESSAGES.DisengageRejectReason.notRegistered
--		"EM_DRJ_notRegistered">--
--<OSS.FIELDNAME 
--		H323-MESSAGES.DisengageRejectReason.requestToDropOther
--		"requestToDropOther">--
--<OSS.DefineName
--		H323-MESSAGES.DisengageRejectReason.requestToDropOther
--		"EM_requestToDropOther">--
--<OSS.FIELDNAME 
--		H323-MESSAGES.DisengageRejectReason.securityDenial
--		"securityDenial">--
--<OSS.DefineName
--		H323-MESSAGES.DisengageRejectReason.securityDenial
--		"EM_DRJ_securityDenial">--

-- ------------------------------------------------------------- --
-- InfoRequest ::= SEQUENCE 
-- {
-- 	requestSeqNum		RequestSeqNum,
-- 	callReferenceValue	CallReferenceValue,
-- 	nonStandardData		NonStandardParameter OPTIONAL,
-- 	replyAddress		TransportAddress OPTIONAL,
-- 	...,
-- 	callIdentifier		CallIdentifier,
-- 	tokens				SEQUENCE OF ClearToken OPTIONAL,
-- 	cryptoTokens		SEQUENCE OF CryptoH323Token OPTIONAL,
-- 	integrityCheckValue	ICV OPTIONAL,
-- 	uuiesRequested		UUIEsRequested OPTIONAL
-- }
-- ------------------------------------------------------------- --

--<ASN1.PDU
--		H323-MESSAGES.InfoRequest>--
--<OSS.TYPENAME 
--		H323-MESSAGES.InfoRequest
--		"EmIRQ">--
--<OSS.FIELDNAME 
--		H323-MESSAGES.InfoRequest.requestSeqNum
--		"requestSeqNum">--
--<OSS.FIELDNAME 
--		H323-MESSAGES.InfoRequest.callReferenceValue
--		"callReferenceValue">--
--<OSS.FIELDNAME 
--		H323-MESSAGES.InfoRequest.nonStandardData
--		"nonStandardData">--
--<OSS.DefineName
--		H323-MESSAGES.InfoRequest.nonStandardData
--		"EM_IRQ_nonStandardData">--
--<OSS.FIELDNAME 
--		H323-MESSAGES.InfoRequest.replyAddress
--		"replyAddress">--
--<OSS.DefineName
--		H323-MESSAGES.InfoRequest.replyAddress
--		"EM_replyAddress">--
--<OSS.FIELDNAME 
--		H323-MESSAGES.InfoRequest.callIdentifier
--		"callIdentifier">--
--<OSS.DefineName
--		H323-MESSAGES.InfoRequest.callIdentifier
--		"EM_IRQ_callIdentifier">--
--<OSS.FIELDNAME 
--		H323-MESSAGES.InfoRequest.tokens
--		"tokens">--
--<OSS.DefineName
--		H323-MESSAGES.InfoRequest.tokens
--		"EM_IRQ_tokens">--
--<OSS.FIELDNAME 
--		H323-MESSAGES.InfoRequest.cryptoTokens
--		"cryptoTokens">--
--<OSS.DefineName
--		H323-MESSAGES.InfoRequest.cryptoTokens
--		"EM_IRQ_cryptoTokens">--
--<OSS.FIELDNAME 
--		H323-MESSAGES.InfoRequest.integrityCheckValue
--		"integrityCheckValue">--
--<OSS.DefineName
--		H323-MESSAGES.InfoRequest.integrityCheckValue
--		"EM_IRQ_integrityCheckValue">--
--<OSS.FIELDNAME 
--		H323-MESSAGES.InfoRequest.uuiesRequested
--		"uuiesRequested">--
--<OSS.DefineName
--		H323-MESSAGES.InfoRequest.uuiesRequested
--		"EM_IRQ_uuiesRequested">--

-- ------------------------------------------------------------- --
-- PDUInfo ::= SEQUENCE
-- {
-- 	h323pdu				H323-UU-PDU,
-- 	sent				BOOLEAN
-- }
-- ------------------------------------------------------------- --

--<ASN1.PDU
--		H323-MESSAGES.PDUInfo>--
--<OSS.TYPENAME 
--		H323-MESSAGES.PDUInfo
--		"EmPduInfo">--
--<OSS.FIELDNAME 
--		H323-MESSAGES.PDUInfo.h323pdu
--		"h323pdu">--
--<OSS.FIELDNAME 
--		H323-MESSAGES.PDUInfo.sent
--		"sent">--

-- ------------------------------------------------------------- --
-- PerCallInfo ::= SEQUENCE
-- {
-- 	nonStandardData		NonStandardParameter OPTIONAL,
-- 	callReferenceValue	CallReferenceValue,
-- 	conferenceID		ConferenceIdentifier,
-- 	originator			BOOLEAN OPTIONAL,
-- 	audio				SeqOfRTPSession OPTIONAL,
-- 	video				SeqOfRTPSession OPTIONAL,
-- 	data				SeqOfTransportChannelInfo OPTIONAL,
-- 	h245				TransportChannelInfo,
-- 	callSignaling		TransportChannelInfo,
-- 	callType			CallType,
-- 	bandWidth			BandWidth,
-- 	callModel			CallModel,
-- 	...,
-- 	callIdentifier		CallIdentifier,
-- 	tokens				SeqOfClearToken OPTIONAL,
-- 	cryptoTokens		SeqOfCryptoH323Token OPTIONAL,
-- 	substituteConfIDs	SeqOfConferenceIdentifier,
-- 	pdu					SeqOfPDUInfo
-- }
-- ------------------------------------------------------------- --

--<ASN1.PDU
--		H323-MESSAGES.PerCallInfo>--
--<OSS.TYPENAME 
--		H323-MESSAGES.PerCallInfo
--		"EmPerCallInfo">--
--<OSS.FIELDNAME 
--		H323-MESSAGES.PerCallInfo.nonStandardData
--		"nonStandardData">--
--<OSS.DefineName
--		H323-MESSAGES.PerCallInfo.nonStandardData
--		"EM_PerCallInfo_nonStandardData">--
--<OSS.FIELDNAME 
--		H323-MESSAGES.PerCallInfo.callReferenceValue
--		"callReferenceValue">--
--<OSS.FIELDNAME 
--		H323-MESSAGES.PerCallInfo.conferenceID
--		"conferenceID">--
--<OSS.FIELDNAME 
--		H323-MESSAGES.PerCallInfo.originator
--		"originator">--
--<OSS.DefineName
--		H323-MESSAGES.PerCallInfo.originator
--		"EM_originator">--
--<OSS.FIELDNAME 
--		H323-MESSAGES.PerCallInfo.audio
--		"audio">--
--<OSS.DefineName
--		H323-MESSAGES.PerCallInfo.audio
--		"EM_audio">--
--<OSS.FIELDNAME 
--		H323-MESSAGES.PerCallInfo.video
--		"video">--
--<OSS.DefineName
--		H323-MESSAGES.PerCallInfo.video
--		"EM_video">--
--<OSS.FIELDNAME 
--		H323-MESSAGES.PerCallInfo.data
--		"data">--
--<OSS.DefineName
--		H323-MESSAGES.PerCallInfo.data
--		"EM_data">--
--<OSS.FIELDNAME 
--		H323-MESSAGES.PerCallInfo.h245
--		"h245">--
--<OSS.FIELDNAME 
--		H323-MESSAGES.PerCallInfo.callSignaling
--		"callSignaling">--
--<OSS.FIELDNAME 
--		H323-MESSAGES.PerCallInfo.callType
--		"callType">--
--<OSS.FIELDNAME 
--		H323-MESSAGES.PerCallInfo.bandWidth
--		"bandWidth">--
--<OSS.FIELDNAME 
--		H323-MESSAGES.PerCallInfo.callModel
--		"callModel">--
--<OSS.FIELDNAME 
--		H323-MESSAGES.PerCallInfo.callIdentifier
--		"callIdentifier">--
--<OSS.DefineName
--		H323-MESSAGES.PerCallInfo.callIdentifier
--		"EM_PerCallInfo_callIdentifier">--
--<OSS.FIELDNAME 
--		H323-MESSAGES.PerCallInfo.tokens
--		"tokens">--
--<OSS.DefineName
--		H323-MESSAGES.PerCallInfo.tokens
--		"EM_PerCallInfo_tokens">--
--<OSS.FIELDNAME 
--		H323-MESSAGES.PerCallInfo.cryptoTokens
--		"cryptoTokens">--
--<OSS.DefineName
--		H323-MESSAGES.PerCallInfo.cryptoTokens
--		"EM_PerCallInfo_cryptoTokens">--
--<OSS.FIELDNAME 
--		H323-MESSAGES.PerCallInfo.substituteConfIDs
--		"substituteConfIDs">--
--<OSS.DefineName
--		H323-MESSAGES.PerCallInfo.substituteConfIDs
--		"EM_substituteConfIDs">--
--<OSS.FIELDNAME 
--		H323-MESSAGES.PerCallInfo.pdu
--		"pdu">--
--<OSS.DefineName
--		H323-MESSAGES.PerCallInfo.pdu
--		"EM_pdu">--

-- ------------------------------------------------------------- --
-- InfoRequestResponse ::= SEQUENCE
-- {
-- 	nonStandardData		NonStandardParameter OPTIONAL,
-- 	requestSeqNum		RequestSeqNum,
-- 	endpointType		EndpointType,
-- 	endpointIdentifier	EndpointIdentifier,
-- 	rasAddress			TransportAddress,
-- 	callSignalAddress	SeqOfTransportAddress,
-- 	endpointAlias		SeqOfAliasAddress OPTIONAL,
-- 	perCallInfo			SeqOfPerCallInfo OPTIONAL,
-- 	...,
-- 	tokens				SeqOfClearToken OPTIONAL,
-- 	cryptoTokens		SeqOfCryptoH323Token OPTIONAL,
-- 	integrityCheckValue	ICV OPTIONAL,
-- 	needResponse		BOOLEAN
-- }
-- ------------------------------------------------------------- --

--<ASN1.PDU
--		H323-MESSAGES.InfoRequestResponse>--
--<OSS.TYPENAME 
--		H323-MESSAGES.InfoRequestResponse
--		"EmIRR">--
--<OSS.FIELDNAME 
--		H323-MESSAGES.InfoRequestResponse.nonStandardData
--		"nonStandardData">--
--<OSS.DefineName
--		H323-MESSAGES.InfoRequestResponse.nonStandardData
--		"EM_IRR_nonStandardData">--
--<OSS.FIELDNAME 
--		H323-MESSAGES.InfoRequestResponse.requestSeqNum
--		"requestSeqNum">--
--<OSS.FIELDNAME 
--		H323-MESSAGES.InfoRequestResponse.endpointType
--		"endpointType">--
--<OSS.FIELDNAME 
--		H323-MESSAGES.InfoRequestResponse.endpointIdentifier
--		"endpointIdentifier">--
--<OSS.FIELDNAME 
--		H323-MESSAGES.InfoRequestResponse.rasAddress
--		"rasAddress">--
--<OSS.FIELDNAME 
--		H323-MESSAGES.InfoRequestResponse.callSignalAddress
--		"callSignalAddress">--
--<OSS.FIELDNAME 
--		H323-MESSAGES.InfoRequestResponse.endpointAlias
--		"endpointAlias">--
--<OSS.DefineName
--		H323-MESSAGES.InfoRequestResponse.endpointAlias
--		"EM_IRR_endpointAlias">--
--<OSS.FIELDNAME 
--		H323-MESSAGES.InfoRequestResponse.perCallInfo
--		"perCallInfo">--
--<OSS.DefineName
--		H323-MESSAGES.InfoRequestResponse.perCallInfo
--		"EM_perCallInfo">--
--<OSS.FIELDNAME 
--		H323-MESSAGES.InfoRequestResponse.tokens
--		"tokens">--
--<OSS.DefineName
--		H323-MESSAGES.InfoRequestResponse.tokens
--		"EM_IRR_tokens">--
--<OSS.FIELDNAME 
--		H323-MESSAGES.InfoRequestResponse.cryptoTokens
--		"cryptoTokens">--
--<OSS.DefineName
--		H323-MESSAGES.InfoRequestResponse.cryptoTokens
--		"EM_IRR_cryptoTokens">--
--<OSS.FIELDNAME 
--		H323-MESSAGES.InfoRequestResponse.integrityCheckValue
--		"integrityCheckValue">--
--<OSS.DefineName
--		H323-MESSAGES.InfoRequestResponse.integrityCheckValue
--		"EM_IRR_integrityCheckValue">--
--<OSS.FIELDNAME 
--		H323-MESSAGES.InfoRequestResponse.needResponse
--		"needResponse">--
--<OSS.DefineName
--		H323-MESSAGES.InfoRequestResponse.needResponse
--		"EM_needResponse">--

-- ------------------------------------------------------------- --
-- TransportChannelInfo ::= SEQUENCE
-- {
-- 	sendAddress		TransportAddress OPTIONAL,
-- 	recvAddress		TransportAddress OPTIONAL,
-- 	...
-- }
-- ------------------------------------------------------------- --

--<ASN1.PDU
--		H323-MESSAGES.TransportChannelInfo>--
--<OSS.TYPENAME 
--		H323-MESSAGES.TransportChannelInfo
--		"EmTransportChannelInfo">--
--<OSS.FIELDNAME 
--		H323-MESSAGES.TransportChannelInfo.sendAddress
--		"sendAddress">--
--<OSS.DefineName
--		H323-MESSAGES.TransportChannelInfo.sendAddress
--		"EM_sendAddress">--
--<OSS.FIELDNAME 
--		H323-MESSAGES.TransportChannelInfo.recvAddress
--		"recvAddress">--
--<OSS.DefineName
--		H323-MESSAGES.TransportChannelInfo.recvAddress
--		"EM_recvAddress">--

-- ------------------------------------------------------------- --
-- RTPSession ::= SEQUENCE
-- {
-- 	rtpAddress		TransportChannelInfo,
-- 	rtcpAddress		TransportChannelInfo,
-- 	cname			PrintableString,
-- 	ssrc			INTEGER (1..4294967295),
-- 	sessionId		INTEGER (1..255),
-- 	associatedSessionIds	SEQUENCE OF INTEGER (1..255),
-- 	...
-- }
-- ------------------------------------------------------------- --

--<ASN1.PDU
--		H323-MESSAGES.RTPSession>--
--<OSS.TYPENAME 
--		H323-MESSAGES.RTPSession
--		"EmRTPSession">--
--<OSS.FIELDNAME 
--		H323-MESSAGES.RTPSession.rtpAddress
--		"rtpAddress">--
--<OSS.FIELDNAME 
--		H323-MESSAGES.RTPSession.rtcpAddress
--		"rtcpAddress">--
--<OSS.FIELDNAME 
--		H323-MESSAGES.RTPSession.cname
--		"cname">--
--<OSS.POINTER 
--		H323-MESSAGES.RTPSession.cname>--
--<OSS.FIELDNAME 
--		H323-MESSAGES.RTPSession.ssrc
--		"ssrc">--
--<OSS.FIELDNAME 
--		H323-MESSAGES.RTPSession.sessionId
--		"sessionId">--
--<OSS.TYPENAME
--		H323-MESSAGES.RTPSession.associatedSessionIds
--		"EmSeqOfAssociatedSessionIds">--
--<OSS.FIELDNAME 
--		H323-MESSAGES.RTPSession.associatedSessionIds
--		"associatedSessionIds">--

-- ------------------------------------------------------------- --
-- InfoRequestAck ::= SEQUENCE 
-- {
-- 	requestSeqNum		RequestSeqNum,
-- 	nonStandardData		NonStandardParameter OPTIONAL,
-- 	tokens				SEQUENCE OF ClearToken OPTIONAL,
-- 	cryptoTokens		SEQUENCE OF CryptoH323Token OPTIONAL,
-- 	integrityCheckValue	ICV OPTIONAL,
-- 	...
-- }
-- ------------------------------------------------------------- --

--<ASN1.PDU
--		H323-MESSAGES.InfoRequestAck>--
--<OSS.TYPENAME 
--		H323-MESSAGES.InfoRequestAck
--		"EmIACK">--
--<OSS.FIELDNAME 
--		H323-MESSAGES.InfoRequestAck.requestSeqNum
--		"requestSeqNum">--
--<OSS.FIELDNAME 
--		H323-MESSAGES.InfoRequestAck.nonStandardData
--		"nonStandardData">--
--<OSS.DefineName
--		H323-MESSAGES.InfoRequestAck.nonStandardData
--		"EM_IACK_nonStandardData">--
--<OSS.FIELDNAME 
--		H323-MESSAGES.InfoRequestAck.tokens
--		"tokens">--
--<OSS.DefineName
--		H323-MESSAGES.InfoRequestAck.tokens
--		"EM_IACK_tokens">--
--<OSS.FIELDNAME 
--		H323-MESSAGES.InfoRequestAck.cryptoTokens
--		"cryptoTokens">--
--<OSS.DefineName
--		H323-MESSAGES.InfoRequestAck.cryptoTokens
--		"EM_IACK_cryptoTokens">--
--<OSS.FIELDNAME 
--		H323-MESSAGES.InfoRequestAck.integrityCheckValue
--		"integrityCheckValue">--
--<OSS.DefineName
--		H323-MESSAGES.InfoRequestAck.integrityCheckValue
--		"EM_IACK_integrityCheckValue">--

-- ------------------------------------------------------------- --
-- InfoRequestNak ::= SEQUENCE 
-- {
-- 	requestSeqNum		RequestSeqNum,
-- 	nonStandardData		NonStandardParameter OPTIONAL,
-- 	nakReason			InfoRequestNakReason,
-- 	altGKInfo			AltGKInfo OPTIONAL,
-- 	tokens				SEQUENCE OF ClearToken OPTIONAL,
-- 	cryptoTokens		SEQUENCE OF CryptoH323Token OPTIONAL,
-- 	integrityCheckValue	ICV OPTIONAL,
-- 	...
-- }
-- ------------------------------------------------------------- --

--<ASN1.PDU
--		H323-MESSAGES.InfoRequestNak>--
--<OSS.TYPENAME 
--		H323-MESSAGES.InfoRequestNak
--		"EmINAK">--
--<OSS.FIELDNAME 
--		H323-MESSAGES.InfoRequestNak.requestSeqNum
--		"requestSeqNum">--
--<OSS.FIELDNAME 
--		H323-MESSAGES.InfoRequestNak.nonStandardData
--		"nonStandardData">--
--<OSS.DefineName
--		H323-MESSAGES.InfoRequestNak.nonStandardData
--		"EM_INAK_nonStandardData">--
--<OSS.FIELDNAME 
--		H323-MESSAGES.InfoRequestNak.nakReason
--		"nakReason">--
--<OSS.FIELDNAME 
--		H323-MESSAGES.InfoRequestNak.altGKInfo
--		"altGKInfo">--
--<OSS.DefineName
--		H323-MESSAGES.InfoRequestNak.altGKInfo
--		"EM_INAK_altGKInfo">--
--<OSS.FIELDNAME 
--		H323-MESSAGES.InfoRequestNak.tokens
--		"tokens">--
--<OSS.DefineName
--		H323-MESSAGES.InfoRequestNak.tokens
--		"EM_INAK_tokens">--
--<OSS.FIELDNAME 
--		H323-MESSAGES.InfoRequestNak.cryptoTokens
--		"cryptoTokens">--
--<OSS.DefineName
--		H323-MESSAGES.InfoRequestNak.cryptoTokens
--		"EM_INAK_cryptoTokens">--
--<OSS.FIELDNAME 
--		H323-MESSAGES.InfoRequestNak.integrityCheckValue
--		"integrityCheckValue">--
--<OSS.DefineName
--		H323-MESSAGES.InfoRequestNak.integrityCheckValue
--		"EM_INAK_integrityCheckValue">--

-- ------------------------------------------------------------- --
-- InfoRequestNakReason ::= CHOICE
-- {
-- 	notRegistered		NULL,	
-- 	securityDenial		NULL,
-- 	undefinedReason		NULL,
-- 	...
-- }
-- ------------------------------------------------------------- --

--<ASN1.PDU
--		H323-MESSAGES.InfoRequestNakReason>--
--<OSS.TYPENAME 
--		H323-MESSAGES.InfoRequestNakReason
--		"EmINAKReason">--
--<OSS.FIELDNAME 
--		H323-MESSAGES.InfoRequestNakReason.notRegistered
--		"notRegistered">--
--<OSS.DefineName
--		H323-MESSAGES.InfoRequestNakReason.notRegistered
--		"EM_INAK_notRegistered">--
--<OSS.FIELDNAME 
--		H323-MESSAGES.InfoRequestNakReason.securityDenial
--		"securityDenial">--
--<OSS.DefineName
--		H323-MESSAGES.InfoRequestNakReason.securityDenial
--		"EM_INAK_securityDenial">--
--<OSS.FIELDNAME 
--		H323-MESSAGES.InfoRequestNakReason.undefinedReason
--		"undefinedReason">--
--<OSS.DefineName
--		H323-MESSAGES.InfoRequestNakReason.undefinedReason
--		"EM_INAK_undefinedReason">--

-- ------------------------------------------------------------- --
-- NonStandardMessage ::= SEQUENCE
-- {
-- 	requestSeqNum		RequestSeqNum,
-- 	nonStandardData		NonStandardParameter,
-- 	...,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.NonStandardMessage>--
--<OSS.TYPENAME 
--		H323-MESSAGES.NonStandardMessage
--		"EmNSM">--
--<OSS.FIELDNAME 
--		H323-MESSAGES.NonStandardMessage.requestSeqNum
--		"requestSeqNum">--
--<OSS.FIELDNAME 
--		H323-MESSAGES.NonStandardMessage.nonStandardData
--		"nonStandardData">--
--<OSS.FIELDNAME 
--		H323-MESSAGES.NonStandardMessage.tokens
--		"tokens">--
--<OSS.DefineName
--		H323-MESSAGES.NonStandardMessage.tokens
--		"EM_NSM_tokens">--
--<OSS.FIELDNAME 
--		H323-MESSAGES.NonStandardMessage.cryptoTokens
--		"cryptoTokens">--
--<OSS.DefineName
--		H323-MESSAGES.NonStandardMessage.cryptoTokens
--		"EM_NSM_cryptoTokens">--
--<OSS.FIELDNAME 
--		H323-MESSAGES.NonStandardMessage.integrityCheckValue
--		"integrityCheckValue">--
--<OSS.DefineName
--		H323-MESSAGES.NonStandardMessage.integrityCheckValue
--		"EM_NSM_integrityCheckValue">--

-- ------------------------------------------------------------- --
-- UnknownMessageResponse ::= SEQUENCE	
-- {
-- 	requestSeqNum		RequestSeqNum,
-- 	...,
-- 	tokens				SEQUENCE OF ClearToken OPTIONAL,
-- 	cryptoTokens		SEQUENCE OF CryptoH323Token OPTIONAL,
-- 	integrityCheckValue	ICV OPTIONAL
-- }
-- ------------------------------------------------------------- --

--<ASN1.PDU
--		H323-MESSAGES.UnknownMessageResponse>--
--<OSS.TYPENAME 
--		H323-MESSAGES.UnknownMessageResponse
--		"EmXRS">--
--<OSS.FIELDNAME 
--		H323-MESSAGES.UnknownMessageResponse.requestSeqNum
--		"requestSeqNum">--
--<OSS.FIELDNAME 
--		H323-MESSAGES.UnknownMessageResponse.tokens
--		"tokens">--
--<OSS.DefineName
--		H323-MESSAGES.UnknownMessageResponse.tokens
--		"EM_XRS_tokens">--
--<OSS.FIELDNAME 
--		H323-MESSAGES.UnknownMessageResponse.cryptoTokens
--		"cryptoTokens">--
--<OSS.DefineName
--		H323-MESSAGES.UnknownMessageResponse.cryptoTokens
--		"EM_XRS_cryptoTokens">--
--<OSS.FIELDNAME 
--		H323-MESSAGES.UnknownMessageResponse.integrityCheckValue
--		"integrityCheckValue">--
--<OSS.DefineName
--		H323-MESSAGES.UnknownMessageResponse.integrityCheckValue
--		"EM_XRS_integrityCheckValue">--

-- ------------------------------------------------------------- --
-- RequestInProgress ::= SEQUENCE	
-- {
-- 	requestSeqNum		RequestSeqNum,
-- 	nonStandardData		NonStandardParameter OPTIONAL,
-- 	tokens				SEQUENCE OF ClearToken OPTIONAL,
-- 	cryptoTokens		SEQUENCE OF CryptoH323Token OPTIONAL,
-- 	integrityCheckValue	ICV OPTIONAL,
-- 	delay				INTEGER(1..65535),
-- 	...
-- }
-- ------------------------------------------------------------- --

--<ASN1.PDU
--		H323-MESSAGES.RequestInProgress>--
--<OSS.TYPENAME 
--		H323-MESSAGES.RequestInProgress
--		"EmRIP">--
--<OSS.FIELDNAME 
--		H323-MESSAGES.RequestInProgress.requestSeqNum
--		"requestSeqNum">--
--<OSS.FIELDNAME 
--		H323-MESSAGES.RequestInProgress.nonStandardData
--		"nonStandardData">--
--<OSS.DefineName
--		H323-MESSAGES.RequestInProgress.nonStandardData
--		"EM_RIP_nonStandardData">--
--<OSS.FIELDNAME 
--		H323-MESSAGES.RequestInProgress.tokens
--		"tokens">--
--<OSS.DefineName
--		H323-MESSAGES.RequestInProgress.tokens
--		"EM_RIP_tokens">--
--<OSS.FIELDNAME 
--		H323-MESSAGES.RequestInProgress.cryptoTokens
--		"cryptoTokens">--
--<OSS.DefineName
--		H323-MESSAGES.RequestInProgress.cryptoTokens
--		"EM_RIP_cryptoTokens">--
--<OSS.FIELDNAME 
--		H323-MESSAGES.RequestInProgress.integrityCheckValue
--		"integrityCheckValue">--
--<OSS.DefineName
--		H323-MESSAGES.RequestInProgress.integrityCheckValue
--		"EM_RIP_integrityCheckValue">--
--<OSS.FIELDNAME 
--		H323-MESSAGES.RequestInProgress.delay
--		"delay">--

-- ------------------------------------------------------------- --
-- ResourcesAvailableIndicate ::= SEQUENCE 
-- {
-- 	requestSeqNum			RequestSeqNum,
-- 	protocolIdentifier		ProtocolIdentifier,
-- 	nonStandardData			NonStandardParameter OPTIONAL,
-- 	endpointIdentifier		EndpointIdentifier,
-- 	protocols				SEQUENCE OF SupportedProtocols,
-- 	almostOutOfResources	BOOLEAN,
-- 	tokens					SEQUENCE OF ClearToken OPTIONAL,
-- 	cryptoTokens			SEQUENCE OF CryptoH323Token OPTIONAL,
-- 	integrityCheckValue		ICV OPTIONAL,
-- 	...
-- }
-- ------------------------------------------------------------- --

--<ASN1.PDU
--		H323-MESSAGES.ResourcesAvailableIndicate>--
--<OSS.TYPENAME 
--		H323-MESSAGES.ResourcesAvailableIndicate
--		"EmRAI">--
--<OSS.FIELDNAME 
--		H323-MESSAGES.ResourcesAvailableIndicate.requestSeqNum
--		"requestSeqNum">--
--<OSS.FIELDNAME 
--		H323-MESSAGES.ResourcesAvailableIndicate.protocolIdentifier
--		"protocolIdentifier">--
--<OSS.FIELDNAME 
--		H323-MESSAGES.ResourcesAvailableIndicate.nonStandardData
--		"nonStandardData">--
--<OSS.DefineName
--		H323-MESSAGES.ResourcesAvailableIndicate.nonStandardData
--		"EM_RAI_nonStandardData">--
--<OSS.FIELDNAME 
--		H323-MESSAGES.ResourcesAvailableIndicate.endpointIdentifier
--		"endpointIdentifier">--
--<OSS.FIELDNAME 
--		H323-MESSAGES.ResourcesAvailableIndicate.protocols
--		"protocols">--
--<OSS.FIELDNAME 
--		H323-MESSAGES.ResourcesAvailableIndicate.almostOutOfResources
--		"almostOutOfResources">--
--<OSS.FIELDNAME 
--		H323-MESSAGES.ResourcesAvailableIndicate.tokens
--		"tokens">--
--<OSS.DefineName
--		H323-MESSAGES.ResourcesAvailableIndicate.tokens
--		"EM_RAI_tokens">--
--<OSS.FIELDNAME 
--		H323-MESSAGES.ResourcesAvailableIndicate.cryptoTokens
--		"cryptoTokens">--
--<OSS.DefineName
--		H323-MESSAGES.ResourcesAvailableIndicate.cryptoTokens
--		"EM_RAI_cryptoTokens">--
--<OSS.FIELDNAME 
--		H323-MESSAGES.ResourcesAvailableIndicate.integrityCheckValue
--		"integrityCheckValue">--
--<OSS.DefineName
--		H323-MESSAGES.ResourcesAvailableIndicate.integrityCheckValue
--		"EM_RAI_integrityCheckValue">--

-- ------------------------------------------------------------- --
-- ResourcesAvailableConfirm ::= SEQUENCE 
-- {
-- 	requestSeqNum		RequestSeqNum,
-- 	protocolIdentifier	ProtocolIdentifier,
-- 	nonStandardData		NonStandardParameter OPTIONAL,
-- 	tokens				SEQUENCE OF ClearToken OPTIONAL,
-- 	cryptoTokens		SEQUENCE OF CryptoH323Token OPTIONAL,
-- 	integrityCheckValue	ICV OPTIONAL,
-- 	...	
-- }
-- ------------------------------------------------------------- --

--<ASN1.PDU
--		H323-MESSAGES.ResourcesAvailableConfirm>--
--<OSS.TYPENAME 
--		H323-MESSAGES.ResourcesAvailableConfirm
--		"EmRAC">--
--<OSS.FIELDNAME 
--		H323-MESSAGES.ResourcesAvailableConfirm.requestSeqNum
--		"requestSeqNum">--
--<OSS.FIELDNAME 
--		H323-MESSAGES.ResourcesAvailableConfirm.protocolIdentifier
--		"protocolIdentifier">--
--<OSS.FIELDNAME 
--		H323-MESSAGES.ResourcesAvailableConfirm.nonStandardData
--		"nonStandardData">--
--<OSS.DefineName
--		H323-MESSAGES.ResourcesAvailableConfirm.nonStandardData
--		"EM_RAC_nonStandardData">--
--<OSS.FIELDNAME 
--		H323-MESSAGES.ResourcesAvailableConfirm.tokens
--		"tokens">--
--<OSS.DefineName
--		H323-MESSAGES.ResourcesAvailableConfirm.tokens
--		"EM_RAC_tokens">--
--<OSS.FIELDNAME 
--		H323-MESSAGES.ResourcesAvailableConfirm.cryptoTokens
--		"cryptoTokens">--
--<OSS.DefineName
--		H323-MESSAGES.ResourcesAvailableConfirm.cryptoTokens
--		"EM_RAC_cryptoTokens">--
--<OSS.FIELDNAME 
--		H323-MESSAGES.ResourcesAvailableConfirm.integrityCheckValue
--		"integrityCheckValue">--
--<OSS.DefineName
--		H323-MESSAGES.ResourcesAvailableConfirm.integrityCheckValue
--		"EM_RAC_integrityCheckValue">--

-- ------------------------------------------------------------- --
-- END		
-- ------------------------------------------------------------- --
